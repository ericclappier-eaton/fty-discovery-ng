EATON-GENESIS-II-MIB DEFINITIONS ::= BEGIN

IMPORTS
   enterprises                  FROM RFC1155-SMI
   DisplayString                                FROM RFC1213-MIB
   OBJECT-TYPE                                  FROM RFC-1212
   TRAP-TYPE                                    FROM RFC-1215;

eaton                               OBJECT IDENTIFIER ::=  { enterprises 17373 }

genesis2                OBJECT IDENTIFIER ::=  { eaton 3 }
productInfo                         OBJECT IDENTIFIER ::=  { genesis2 1 }
sensorData                          OBJECT IDENTIFIER ::=  { genesis2 2 }



productTitle    OBJECT-TYPE
   SYNTAX DisplayString
   ACCESS read-only
   STATUS mandatory
   DESCRIPTION
      "Name of product"
   ::= { productInfo 1 }

productVersion    OBJECT-TYPE
   SYNTAX DisplayString
   ACCESS read-only
   STATUS mandatory
   DESCRIPTION
      "Firmware version"
   ::= { productInfo 2 }

productName    OBJECT-TYPE
   SYNTAX DisplayString
   ACCESS read-only
   STATUS mandatory
   DESCRIPTION
      "Unit friendly name"
   ::= { productInfo 3 }

productMAC    OBJECT-TYPE
   SYNTAX DisplayString
   ACCESS read-only
   STATUS mandatory
   DESCRIPTION
      "Unit MAC address"
   ::= { productInfo 4 }

productIP    OBJECT-TYPE
   SYNTAX DisplayString
   ACCESS read-only
   STATUS mandatory
   DESCRIPTION
      "IP address of the unit"
   ::= { productInfo 5 }



intDeciAmpsCT1    OBJECT-TYPE
   SYNTAX INTEGER(-1..300)
   UNITS "0.1 Amps"
   ACCESS read-only
   STATUS mandatory
   DESCRIPTION
      "Current Reading from CT1 in deci-Amps, a reading of -1 
        means the CT is unavailable on this unit"
   ::= { sensorData 1 }

intDeciAmpsCT2    OBJECT-TYPE
   SYNTAX INTEGER(-1..300)
   UNITS "0.1 Amps"
   ACCESS read-only
   STATUS mandatory
   DESCRIPTION
      "Current Reading from CT2 in deci-Amps, a reading of -1 
        means the CT is unavailable on this unit"
   ::= { sensorData 2 }

intDeciAmpsCT3    OBJECT-TYPE
   SYNTAX INTEGER(-1..300)
   UNITS "0.1 Amps"
   ACCESS read-only
   STATUS mandatory
   DESCRIPTION
      "Current Reading from CT3 in deci-Amps, a reading of -1 
        means the CT is unavailable on this unit"
   ::= { sensorData 3 }

intDeciAmpsCT4    OBJECT-TYPE
   SYNTAX INTEGER(-1..300)
   UNITS "0.1 Amps"
   ACCESS read-only
   STATUS mandatory
   DESCRIPTION
      "Current Reading from CT4 in deci-Amps, a reading of -1 
        means the CT is unavailable on this unit"
   ::= { sensorData 4 }

intDeciAmpsCT5    OBJECT-TYPE
   SYNTAX INTEGER(-1..300)
   UNITS "0.1 Amps"
   ACCESS read-only
   STATUS mandatory
   DESCRIPTION
      "Current Reading from CT5 in deci-Amps, a reading of -1 
        means the CT is unavailable on this unit"
   ::= { sensorData 5 }

intDeciAmpsCT6    OBJECT-TYPE
   SYNTAX INTEGER(-1..300)
   UNITS "0.1 Amps"
   ACCESS read-only
   STATUS mandatory
   DESCRIPTION
      "Current Reading from CT6 in deci-Amps, a reading of -1 
        means the CT is unavailable on this unit"
   ::= { sensorData 6 }

intDeciAmpsCT7    OBJECT-TYPE
   SYNTAX INTEGER(-1..300)
   UNITS "0.1 Amps"
   ACCESS read-only
   STATUS mandatory
   DESCRIPTION
      "Current Reading from CT7 in deci-Amps, a reading of -1 
        means the CT is unavailable on this unit"
   ::= { sensorData 7 }

intDeciAmpsCT8    OBJECT-TYPE
   SYNTAX INTEGER(-1..300)
   UNITS "0.1 Amps"
   ACCESS read-only
   STATUS mandatory
   DESCRIPTION
      "Current Reading from CT8 in deci-Amps, a reading of -1 
        means the CT is unavailable on this unit"
   ::= { sensorData 8 }



intDeciAmpsCT1TRAP TRAP-TYPE
ENTERPRISE eaton
VARIABLES { intDeciAmpsCT1 }
DESCRIPTION "DeciAmps CT1 Trap"
::= 1

intDeciAmpsCT2TRAP TRAP-TYPE
ENTERPRISE eaton
VARIABLES { intDeciAmpsCT2 }
DESCRIPTION "DeciAmps CT2 Trap"
::= 2

intDeciAmpsCT3TRAP TRAP-TYPE
ENTERPRISE eaton
VARIABLES { intDeciAmpsCT3 }
DESCRIPTION "DeciAmps CT3 Trap"
::= 3

intDeciAmpsCT4TRAP TRAP-TYPE
ENTERPRISE eaton
VARIABLES { intDeciAmpsCT4 }
DESCRIPTION "DeciAmps CT4 Trap"
::= 4

intDeciAmpsCT5TRAP TRAP-TYPE
ENTERPRISE eaton
VARIABLES { intDeciAmpsCT5 }
DESCRIPTION "DeciAmps CT5 Trap"
::= 5

intDeciAmpsCT6TRAP TRAP-TYPE
ENTERPRISE eaton
VARIABLES { intDeciAmpsCT6 }
DESCRIPTION "DeciAmps CT6 Trap"
::= 6

intDeciAmpsCT7TRAP TRAP-TYPE
ENTERPRISE eaton
VARIABLES { intDeciAmpsCT7 }
DESCRIPTION "DeciAmps CT7 Trap"
::= 7

intDeciAmpsCT8TRAP TRAP-TYPE
ENTERPRISE eaton
VARIABLES { intDeciAmpsCT8 }
DESCRIPTION "DeciAmps CT8 Trap"
::= 8



END
