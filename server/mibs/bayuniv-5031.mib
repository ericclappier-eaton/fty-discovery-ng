-- BAY TECHNICAL ASSOCIATES (BAYTECH) MIB

-- Copyright (c) Bay Technical Associates 2000 - 2017.
-- Version : 5.03.1

-- Title: TOP LEVEL BAYTECH MIB for all baytech devices

-- *************************************************************************
-- ************************************************************************
-- Baytech-MIB { iso org(3) dod(6) internet(1) private(4)
--    enterprises(1) baytech(4779) }

--
-- Module/Port MIB definitions are included below.  These have been commented
-- out.  To access RPCs & outlets by module/port indexing, (in addition to
-- port indexing, the default method) uncomment this section prior to
-- compiling the MIB for your browser.
--


Baytech-MIB-503-1 DEFINITIONS ::= BEGIN

IMPORTS
   enterprises, IpAddress, Gauge, TimeTicks     FROM RFC1155-SMI
   DisplayString                                FROM RFC1213-MIB
   OBJECT-TYPE                                  FROM RFC-1212
   TRAP-TYPE                                    FROM RFC-1215;

baytech                         OBJECT IDENTIFIER ::=  { enterprises 4779 }
v2Notifications                 OBJECT IDENTIFIER ::=  { baytech 0 }

btadevices                      OBJECT IDENTIFIER ::=  { baytech 1 }
mtrapargs                       OBJECT IDENTIFIER ::=  { baytech 3 }

sBTAIdent                       OBJECT IDENTIFIER ::=  { btadevices 1 }
sBTANetworkConfig               OBJECT IDENTIFIER ::=  { btadevices 2 }
sBTAModules                     OBJECT IDENTIFIER ::=  { btadevices 3 }
sBTAControl                     OBJECT IDENTIFIER ::=  { btadevices 4 }
sBTAFileTransfer                OBJECT IDENTIFIER ::=  { btadevices 5 }
sBTAEnvironmental               OBJECT IDENTIFIER ::=  { btadevices 6 }
sBTAAlarms                      OBJECT IDENTIFIER ::=  { btadevices 7 }

-- object types

-- the sBTAIdent group

sBTAIdentFirmwareRev OBJECT-TYPE
   SYNTAX DisplayString
   ACCESS read-only
   STATUS mandatory
   DESCRIPTION
      "An 8 byte ID string identifying the DS72 firmware revision.
       This value is set at the factory."
   ::= {  sBTAIdent 1 }

sBTAIdentSerialNumber OBJECT-TYPE
   SYNTAX INTEGER
   ACCESS read-only
   STATUS mandatory
   DESCRIPTION
      "A number identifying the serial number of the DS72.
      This value is set at the factory."
   ::= { sBTAIdent 2 }

sBTAIdentUnitName OBJECT-TYPE
   SYNTAX DisplayString (SIZE(64))
   ACCESS read-write
   STATUS mandatory
   DESCRIPTION
      "A 64-character string identifying the name (UnitID) of the DS62 or power control device.
       This value is set at the factory to a default of DS62 or URPC, as applicable."
   ::= { sBTAIdent 3 }

--sBTAIdentUnitDescription OBJECT-TYPE
--   SYNTAX DisplayString
--   ACCESS read-write
--   STATUS mandatory
--   DESCRIPTION
--      "A 64-character string that can be used by the user for additional
--       information describing the unit.
--       This value is set at the factory to a default of NULL."
--   ::= { sBTAIdent 4 }

-- the sBTANetworkConfig group

sBTANetworkConfigBootpEnable OBJECT-TYPE
   SYNTAX INTEGER  {
   disabled (0),
   enabled (1)
   }
   ACCESS read-write
   STATUS mandatory
   DESCRIPTION
      "Enables/disables bootp.  Bootp will not take effect until the unit is reseted."
   ::= { sBTANetworkConfig 1 }

sBTANetworkConfigDHCPEnable OBJECT-TYPE
   SYNTAX INTEGER  {
   disabled (0),
   enabled (1)
   }
   ACCESS read-write
   STATUS mandatory
   DESCRIPTION
      "Enables/disables DHCP.  DHCP will not take effect until the unit is reseted."
   ::= { sBTANetworkConfig 2 }

sBTANetworkConfigSSHEnable OBJECT-TYPE
   SYNTAX INTEGER  {
   disabled (0),
   enabled (1)
   }
   ACCESS read-write
   STATUS mandatory
   DESCRIPTION
      "Enables/disables SSH logins.
       Disable/enable SSH will take effect after the unit is reseted."
   ::= { sBTANetworkConfig 3 }

sBTANetworkConfigTelnetEnable OBJECT-TYPE
   SYNTAX INTEGER  {
   disabled (0),
   enabled (1)
   }
   ACCESS read-write
   STATUS mandatory
   DESCRIPTION
      "Enables/disables telnet. "
   ::= { sBTANetworkConfig 4 }


sBTANetworkConfigActivityTimeout OBJECT-TYPE
   SYNTAX INTEGER
   ACCESS read-write
   STATUS mandatory
   DESCRIPTION
      "A value from 0 to 120.  0 disables activity timeouts.
       Value represents minutes of non-activity before telnet / SSH sessions are
       automatically logged out.
       Default is 0."
   ::= { sBTANetworkConfig 5 }


sBTANetworkConfigDirectConnEnable OBJECT-TYPE
   SYNTAX INTEGER  {
   disabled (0),
   enabled (1)
   }
   ACCESS read-write
   STATUS mandatory
   DESCRIPTION
      "Enables/disables direct port connection upon login."
   ::= { sBTANetworkConfig 6 }


sBTANetworkConfigSNMP      OBJECT IDENTIFIER ::= { sBTANetworkConfig 8 }
sBTANetworkConfigRadius    OBJECT IDENTIFIER ::= { sBTANetworkConfig 9 }
sBTANetworkConfigWEB        OBJECT IDENTIFIER ::= { sBTANetworkConfig 10 }



-- the sBTANetworkConfigSNMP group

sBTANetworkConfigSNMPReadOnlyCommunity OBJECT-TYPE
   SYNTAX DisplayString
   ACCESS read-write
   STATUS mandatory
   DESCRIPTION
      "The community name to use for read only access.  Maximum len 16 bytes."
   ::= { sBTANetworkConfigSNMP 1 }

sBTANetworkConfigSNMPReadWriteCommunity OBJECT-TYPE
   SYNTAX DisplayString
   ACCESS read-write
   STATUS mandatory
   DESCRIPTION
      "The community name to use for read-write access.  Maximum len 16 bytes."
   ::= { sBTANetworkConfigSNMP 2 }

sBTANetworkConfigSNMPNumTrapReceivers OBJECT-TYPE
   SYNTAX INTEGER
   ACCESS read-only
   STATUS mandatory
   DESCRIPTION
      "The maximum number of managers to send traps to.  Currently 4."
   ::= { sBTANetworkConfigSNMP 3 }

sBTANetworkConfigSNMPTrapReceiverTable OBJECT-TYPE
   SYNTAX SEQUENCE OF SBTANetworkConfigSNMPTrapReceiverEntry
   ACCESS not-accessible
   STATUS mandatory
   DESCRIPTION
      "A list of managers to send traps to.  The number of
       entries is given by the value of sBTANetworkConfigSNMPNumTrapReceivers.
      Maximum number of Trap Receivers is four."
   ::= { sBTANetworkConfigSNMP 4 }

sBTANetworkConfigSNMPTrapReceiverEntry OBJECT-TYPE
   SYNTAX SBTANetworkConfigSNMPTrapReceiverEntry
   ACCESS not-accessible
   STATUS mandatory
   DESCRIPTION
      "Table of managers to send traps to."
   INDEX  { trapIndex}
   ::= { sBTANetworkConfigSNMPTrapReceiverTable 1 }

SBTANetworkConfigSNMPTrapReceiverEntry ::=
   SEQUENCE {
      trapIndex           INTEGER,
      receiverAddress     IpAddress,
      IPv6ReceiverAddress IpAddress,
      addressType         INTEGER   
   }

trapIndex OBJECT-TYPE
   SYNTAX INTEGER
   ACCESS read-only
   STATUS mandatory
   DESCRIPTION
      "The index to a trap receiver entry."
   ::= { sBTANetworkConfigSNMPTrapReceiverEntry 1 }

receiverAddress OBJECT-TYPE
   SYNTAX IpAddress
   ACCESS read-write
   STATUS mandatory
   DESCRIPTION
      "The IP address of the manager to send traps to."
   ::= { sBTANetworkConfigSNMPTrapReceiverEntry 2 }

IPv6ReceiverAddress OBJECT-TYPE
   SYNTAX IpAddress
   ACCESS read-write
   STATUS mandatory
   DESCRIPTION
      "The IP address of the manager to send traps to."
   ::= { sBTANetworkConfigSNMPTrapReceiverEntry 3 }

addressType OBJECT-TYPE
   SYNTAX INTEGER
   ACCESS read-only
   STATUS mandatory
   DESCRIPTION
      "1 - IPv4 address; 2 - IPv6 address"
   ::= { sBTANetworkConfigSNMPTrapReceiverEntry 4 }

-- the sBTANetworkConfigRadius group
-- Radius configuration is Deprecated, but associated OIDs 
-- remain in MIB for backward compatibility.  These will return 
-- empty when walked.

sBTANetworkConfigRadiusEnable OBJECT-TYPE
   SYNTAX INTEGER   {
      disable  (0),
      enable   (1)
   }
   ACCESS read-write
   STATUS mandatory
   DESCRIPTION
      "Enables / disables RADIUS telnet logins.  Deprecated."
   ::= { sBTANetworkConfigRadius 1 }


sBTANetworkConfigRadiusPrimaryServer OBJECT-TYPE
   SYNTAX IpAddress
   ACCESS read-write
   STATUS mandatory
   DESCRIPTION
      "Ip address of the primary RADIUS server.  Deprecated."
   ::= { sBTANetworkConfigRadius 2 }

sBTANetworkConfigRadiusSecondaryServer OBJECT-TYPE
   SYNTAX IpAddress
   ACCESS read-write
   STATUS mandatory
   DESCRIPTION
      "Ip address of the back-up RADIUS server.  Deprecated."
   ::= { sBTANetworkConfigRadius 3 }

sBTANetworkConfigRadiusLocalLogin OBJECT-TYPE
   SYNTAX INTEGER {
      disable  (0),
      enable   (1)
   }
   ACCESS read-write
   STATUS mandatory
   DESCRIPTION
      "Enables / disables the use of local (usernames stored in the DS72) logins
       in the case that both the primary and secondary RADIUS server are not available.
       Deprecated."
   ::= { sBTANetworkConfigRadius 4 }

--------------------------------------------------
--        The sFNetworkConfigWEB Group        --
--------------------------------------------------

sBTANetworkConfigWebEnable OBJECT-TYPE
   SYNTAX INTEGER  {
   disabled (0),
   enabled (1)
   }
   ACCESS read-write
   STATUS mandatory
   DESCRIPTION
       "Enables WEB."
   ::= { sBTANetworkConfigWEB 1 }

sBTANetworkConfigWebSecureEnable OBJECT-TYPE
   SYNTAX INTEGER  {
   disabled (0),
   enabled (1)
   }
   ACCESS read-write
   STATUS mandatory
   DESCRIPTION
       "Enables WEB Security."
   ::= { sBTANetworkConfigWEB 2 }

sBTANetworkConfigWebLoginEnable OBJECT-TYPE
   SYNTAX INTEGER  {
   disabled (0),
   enabled (1)
   }
   ACCESS read-write
   STATUS mandatory
   DESCRIPTION
       "Enables WEB Login."
   ::= { sBTANetworkConfigWEB 3 }

sBTANetworkConfigWebActivityTimeout OBJECT-TYPE
   SYNTAX INTEGER
   ACCESS read-write
   STATUS mandatory
   DESCRIPTION
       "A value from 0 to 120.  0 disables WEB activity timeouts.
       Value represents minutes of non-activity before WEB sessions are
       automatically logged out.  Default is 0."
   ::= { sBTANetworkConfigWEB 4 }


-- the sBTAModules group

sBTAModulesNumberOfModules OBJECT-TYPE
   SYNTAX INTEGER
   ACCESS read-only
   STATUS mandatory
   DESCRIPTION
      "Number of modules installed into the DS unit."
   ::= { sBTAModules 1 }

sBTAModulesModulesInstalled OBJECT-TYPE
   SYNTAX DisplayString
   ACCESS read-only
   STATUS mandatory
   DESCRIPTION
      "A character string listing the modules installed seperated by commas.
       Each module is identifed by a two digit number indicating the slot.
       For example 02,03,04,06 means modules 2,3,4 and 6 are installed."
   ::= { sBTAModules 2 }

sBTAModulesResetModulesCmd OBJECT-TYPE
   SYNTAX INTEGER
   ACCESS read-only
   STATUS deprecated
   DESCRIPTION
      "This command is no longer supported."
   ::= { sBTAModules 3 }

sBTAModulesNumberOfIntelligentModules OBJECT-TYPE
   SYNTAX INTEGER
   ACCESS read-only
   STATUS mandatory
   DESCRIPTION
      "The number of Intelligent Modules installed in the DS Unit."
   ::= { sBTAModules 4 }

sBTAModulesRPC      OBJECT IDENTIFIER ::=  { sBTAModules 5 }
sBTAModulesSerial   OBJECT IDENTIFIER ::=  { sBTAModules 6 }
sBTAModulesModem    OBJECT IDENTIFIER ::=  { sBTAModules 7 }

-- sBTAModulesRPC group

sBTAModulesNumberOfRPCModules OBJECT-TYPE
   SYNTAX INTEGER
   ACCESS read-only
   STATUS mandatory
   DESCRIPTION
      "The number of power control devices installed in the DS Unit."
   ::= { sBTAModulesRPC 1 }

sBTAModulesRPCTable OBJECT-TYPE
   SYNTAX SEQUENCE OF SBTAModulesRPCEntry
   ACCESS not-accessible
   STATUS mandatory
   DESCRIPTION
      "Allows for control of individual outlets and individual power control device modules. "
   ::= { sBTAModulesRPC 2 }

sBTAModulesRPCEntry OBJECT-TYPE
   SYNTAX SBTAModulesRPCEntry
   ACCESS not-accessible
   STATUS mandatory
   DESCRIPTION
      "The RPCs to control and get status on."
   INDEX  { sBTAModulesRPCIndex}
   ::= { sBTAModulesRPCTable 1 }

SBTAModulesRPCEntry ::=
   SEQUENCE {
      sBTAModulesRPCIndex       INTEGER,
      sBTAModulesRPCName        DisplayString,
      sBTAModulesRPCFirmwareVersion     DisplayString,
      sBTAModulesRPCCurrent     INTEGER,
      sBTAModulesRPCMaxCurrent      INTEGER,
      sBTAModulesRPCVoltage     INTEGER,
      sBTAModulesRPCPower       INTEGER,
      sBTAModulesRPCTemperature     INTEGER,
      sBTAModulesRPCRebootTimeout   INTEGER,
      sBTAModulesRPCAllOutletsCmd   INTEGER,
      sBTAModulesRPCAllOutletsStatus    DisplayString,
      sBTAModulesRPCCurrentAlarmThreshold INTEGER,
      sBTAModulesRPCOverVoltageThreshold  INTEGER,
      sBTAModulesRPCUnderVoltageThreshold INTEGER,
      sBTAModulesRPCNumberOfOutlets INTEGER,
      sBTAModulesRPCOverTempThreshold   INTEGER,
      sBTAModulesRPCUnitVA      INTEGER,
      sBTAModulesRPCNumberOfCircuits    INTEGER,
      sBTAModulesRPCLowCurrentThreshold INTEGER,
      sBTAModulesRPCVoltageSource   INTEGER,
      sBTAModulesRPCSourceSwitchCount   INTEGER,
      sBTAModulesRPCNumberOfSensors INTEGER,
      sBTAModulesRPCType            DisplayString,
      sBTAmodulesRPCKWHours         INTEGER,
      sBTAModulesRPCNumberOfInputSources INTEGER,
      sBTAModulesRPCNumberOfInputPhases INTEGER,
      sBTAModulesRPCTempUnits   INTEGER
      
   }

sBTAModulesRPCIndex OBJECT-TYPE
   SYNTAX INTEGER
   ACCESS read-only
   STATUS mandatory
   DESCRIPTION
      "The index into the power control device table.  Indexes for power 
      control devices attached to ds74 modules are calculate with the following formula:
      ((module - 2) * 4) + port.  For example module 3 port 1 = index 5. "
   ::= { sBTAModulesRPCEntry 1 }

sBTAModulesRPCName OBJECT-TYPE
   SYNTAX DisplayString
   ACCESS read-write
   STATUS mandatory
   DESCRIPTION
      "The name (unit id) of the power control device."
   ::= { sBTAModulesRPCEntry 2 }

sBTAModulesRPCFirmwareVersion OBJECT-TYPE
   SYNTAX DisplayString
   ACCESS read-only
   STATUS mandatory
   DESCRIPTION
      "The firware version of the power control device."
   ::= { sBTAModulesRPCEntry 3 }

sBTAModulesRPCCurrent OBJECT-TYPE
   SYNTAX INTEGER
   ACCESS read-only
   STATUS mandatory
   DESCRIPTION
      "The current reading for the power strip.
       If current measurement is not installed this value will always read 0."
   ::= { sBTAModulesRPCEntry 4 }

sBTAModulesRPCMaxCurrent OBJECT-TYPE
   SYNTAX INTEGER
   ACCESS read-write
   STATUS mandatory
   DESCRIPTION
      "The maximum detected current reading for the power strip.
       If current measurement is not installed this value will always read 0.
       Setting this value to 0 will clear the maximum current detected."
   ::= { sBTAModulesRPCEntry 5 }

sBTAModulesRPCVoltage OBJECT-TYPE
   SYNTAX INTEGER
   ACCESS read-only
   STATUS mandatory
   DESCRIPTION
      "The voltage reading for the power strip.
       If voltage measurement is not installed this value will always read 0."
   ::= { sBTAModulesRPCEntry 6 }

sBTAModulesRPCPower OBJECT-TYPE
   SYNTAX INTEGER
   ACCESS read-only
   STATUS mandatory
   DESCRIPTION
      "The power reading for the power strip.
       If power measurement is not installed this value will always read 0."
   ::= { sBTAModulesRPCEntry 7 }

sBTAModulesRPCTemperature OBJECT-TYPE
   SYNTAX INTEGER
   ACCESS read-only
   STATUS mandatory
   DESCRIPTION
      "The temperature reading for the power strip.  Readings are in degrees C.
       If temperature measurement is not installed this value will always read 0."
   ::= { sBTAModulesRPCEntry 8 }

sBTAModulesRPCRebootTimeout OBJECT-TYPE
   SYNTAX INTEGER
   ACCESS read-only
   STATUS mandatory
   DESCRIPTION
      "The length of off time for automatic reboot sequences.
       Currently a read-only value set to the fixed reboot timeout."
   ::= { sBTAModulesRPCEntry 9 }

sBTAModulesRPCAllOutletsCmd OBJECT-TYPE
   SYNTAX INTEGER {
        off         (0),
        on          (1),
        reboot      (2),
        lockon      (3),
        lockoff     (4),
        unlock      (5),
        unknown     (6)
   }
   ACCESS read-write
   STATUS mandatory
   DESCRIPTION
      "Turns all outlets on, off or reboot.
       0 = off
       1 = on
       2 = reboot

       A get will return unknown (6)."
   ::= { sBTAModulesRPCEntry 10 }

sBTAModulesRPCAllOutletsStatus OBJECT-TYPE
   SYNTAX DisplayString
   ACCESS read-only
   STATUS mandatory
   DESCRIPTION
      "Reports status of outlets in a comma deliminated string.
       0 = off
       1 = on
       2 = reboot
       3 = locked on
       4 = locked off"
   ::= { sBTAModulesRPCEntry 11 }

sBTAModulesRPCCurrentAlarmThreshold OBJECT-TYPE
   SYNTAX INTEGER
   ACCESS read-write
   STATUS mandatory
   DESCRIPTION
      "The current alarm threshold level *10.  A value of 105 will set the level to 10.5."
   ::= { sBTAModulesRPCEntry 12 }

sBTAModulesRPCOverVoltageThreshold OBJECT-TYPE
   SYNTAX INTEGER
   ACCESS read-write
   STATUS mandatory
   DESCRIPTION
      "The over voltage alarm threshold level *10.  A value of 105 will set the level to 10.5."
   ::= { sBTAModulesRPCEntry 13 }

sBTAModulesRPCUnderVoltageThreshold OBJECT-TYPE
   SYNTAX INTEGER
   ACCESS read-write
   STATUS mandatory
   DESCRIPTION
      "The under voltage alarm threshold level *10.  A value of 105 will set the level to 10.5."
   ::= { sBTAModulesRPCEntry 14 }

sBTAModulesRPCNumberOfOutlets OBJECT-TYPE
   SYNTAX INTEGER
   ACCESS read-only
   STATUS mandatory
   DESCRIPTION
      "Number of outlets for this power control device.
       This will be the size of outlet table for this power control device index."
   ::= { sBTAModulesRPCEntry 15 }

sBTAModulesRPCOverTempThreshold OBJECT-TYPE
   SYNTAX INTEGER
   ACCESS read-write
   STATUS mandatory
   DESCRIPTION
      "The over temperature alarm threshold level *10.  A value of 505 will set the level to 50.5."
   ::= { sBTAModulesRPCEntry 17 }

sBTAModulesRPCUnitVA OBJECT-TYPE
   SYNTAX INTEGER
   ACCESS read-only
   STATUS mandatory
   DESCRIPTION
      "Total Volt-Amps for this power control device. "
   ::= { sBTAModulesRPCEntry 18 }

sBTAModulesRPCNumberOfCircuits OBJECT-TYPE
   SYNTAX INTEGER
   ACCESS read-only
   STATUS mandatory
   DESCRIPTION
      "Number of Circuits for this power control device. "
   ::= { sBTAModulesRPCEntry 19 }

sBTAModulesRPCLowCurrentThreshold OBJECT-TYPE
   SYNTAX INTEGER
   ACCESS read-write
   STATUS mandatory
   DESCRIPTION
      "Low current threshold for this power control device. "
   ::= { sBTAModulesRPCEntry 20 }

sBTAModulesRPCVoltageSource OBJECT-TYPE
   SYNTAX INTEGER
   ACCESS read-write
   STATUS mandatory
   DESCRIPTION
      "Voltage source for this power control device. "
   ::= { sBTAModulesRPCEntry 21 }

sBTAModulesRPCSourceSwitchCount OBJECT-TYPE
   SYNTAX INTEGER
   ACCESS read-only
   STATUS mandatory
   DESCRIPTION
      "Count of Voltage Source Switches for this power control device. "
   ::= { sBTAModulesRPCEntry 22 }

sBTAModulesRPCNumberOfSensors OBJECT-TYPE
   SYNTAX INTEGER
   ACCESS read-only
   STATUS mandatory
   DESCRIPTION
      "Number of environmental sensors for this power control device. "
   ::= { sBTAModulesRPCEntry 23 }

sBTAModulesRPCType OBJECT-TYPE
   SYNTAX DisplayString
   ACCESS read-only
   STATUS mandatory
   DESCRIPTION
      "The type of RPC installed at the indexed location."
   ::= { sBTAModulesRPCEntry 24 }
   
sBTAmodulesRPCKWHours OBJECT-TYPE
   SYNTAX INTEGER
   ACCESS read-write
   STATUS mandatory
   DESCRIPTION
      "Kilowatt hours for this RPC.  Setting this object
      clears the value, resetting it to 0"
   ::= { sBTAModulesRPCEntry 25 }

sBTAModulesRPCNumberOfInputSources OBJECT-TYPE
   SYNTAX INTEGER
   ACCESS read-only
   STATUS mandatory
   DESCRIPTION
      "The number of power input sources on this power control device."
   ::= { sBTAModulesRPCEntry 26 }

sBTAModulesRPCNumberOfInputPhases  OBJECT-TYPE
   SYNTAX INTEGER
   ACCESS read-only
   STATUS mandatory
   DESCRIPTION
      "The number of input phases on this power control device.
      A return of '0' indicates that an input sensor module is 
      not present in the unit."
   ::= { sBTAModulesRPCEntry 27 }
   
sBTAModulesRPCTempUnits OBJECT-TYPE
   SYNTAX INTEGER
   ACCESS read-write
   STATUS mandatory
   DESCRIPTION
      "Celcius: 1.  Farenheit: 2.  Setting one instance in table
      sets temp units for all connected devices - no mix & match"
   ::= { sBTAModulesRPCEntry 28 }



sBTAModulesRPCOutletTable OBJECT-TYPE
   SYNTAX SEQUENCE OF SBTAModulesRPCOutletEntry
   ACCESS not-accessible
   STATUS mandatory
   DESCRIPTION
      "Allows for control of individual outlets. The number of
       entries is contained in the sBTAModulesRPCOutletTableSize OID."
   ::= { sBTAModulesRPC 3 }

sBTAModulesRPCOutletEntry OBJECT-TYPE
   SYNTAX SBTAModulesRPCOutletEntry
   ACCESS not-accessible
   STATUS mandatory
   DESCRIPTION
      "The outlets to control and get status on."
   INDEX  { sBTAModulesRPCOutletModuleIndex, sBTAModulesRPCOutletIndex}
   ::= { sBTAModulesRPCOutletTable 1 }

SBTAModulesRPCOutletEntry ::=
   SEQUENCE {
      sBTAModulesRPCOutletModuleIndex   INTEGER,
      sBTAModulesRPCOutletIndex         INTEGER,
      sBTAModulesRPCOutletState         INTEGER,
      sBTAModulesRPCOutletName       DisplayString,
      sBTAModulesRPCOutletCurrent       INTEGER,
      sBTAModulesRPCOutletMaxCurrent    INTEGER,
      sBTAModulesRPCOutletVoltage       INTEGER,
      sBTAModulesRPCOutletPower         INTEGER,
      sBTAModulesRPCOutletVA            INTEGER,
      sBTAModulesRPCOutletPowerFactor   INTEGER,
      sBTAModulesRPCOutletCurrentAlarmThreshold      INTEGER,   
      sBTAModulesRPCOutletPowerFactorAlarmThreshold  INTEGER,
      sBTAModulesRPCOutletPowerFactorPowerThreshold  INTEGER,
      sBTAModulesRPCOutletKWHours       INTEGER,
      sBTAModulesRPCOutletType          INTEGER,
      sBTAModulesRPCOutletCircuit       INTEGER
   }

sBTAModulesRPCOutletModuleIndex OBJECT-TYPE
   SYNTAX INTEGER
   ACCESS read-only
   STATUS mandatory
   DESCRIPTION
      "The index to the outlet entry."
   ::= { sBTAModulesRPCOutletEntry 1 }

sBTAModulesRPCOutletIndex OBJECT-TYPE
   SYNTAX INTEGER
   ACCESS read-only
   STATUS mandatory
   DESCRIPTION
      "The index to the outlet entry."
   ::= { sBTAModulesRPCOutletEntry 2 }

sBTAModulesRPCOutletState OBJECT-TYPE
   SYNTAX INTEGER {
        off (0),
        on  (1),
        reboot  (2),
        lockon  (3),
        lockoff (4),
        unlock  (5),
        unknown (6)
   }

   ACCESS read-write
   STATUS mandatory
   DESCRIPTION
       "Getting this variable will return the state of the outlet.
       Valid return states are unknown, on, off, lockon, lockoff.
       0 = off
       1 = on
       2 = reboot
       3 = lockon (outlet is on and no changes are allowed)
       4 = lockoff (outlet is off and no changes are allowed)
       5 = unlock."

   ::= { sBTAModulesRPCOutletEntry 3 }


sBTAModulesRPCOutletName    OBJECT-TYPE
   SYNTAX  DisplayString
   ACCESS  read-write
   STATUS  mandatory
   DESCRIPTION
      "The name of the outlet. Maximum size is 16 characters."

   ::= { sBTAModulesRPCOutletEntry  4 }
   
   
sBTAModulesRPCOutletCurrent     OBJECT-TYPE
   SYNTAX INTEGER
   ACCESS read-only
   STATUS mandatory
   DESCRIPTION
      "The outlet current in tenths of amps."
   ::= { sBTAModulesRPCOutletEntry 5 }

sBTAModulesRPCOutletMaxCurrent      OBJECT-TYPE
   SYNTAX INTEGER
   ACCESS read-only
   STATUS mandatory
   DESCRIPTION
      "The max outlet current in tenths of amps."
   ::= { sBTAModulesRPCOutletEntry 6 }


sBTAModulesRPCOutletVoltage     OBJECT-TYPE
   SYNTAX INTEGER
   ACCESS read-only
   STATUS mandatory
   DESCRIPTION
      "The outlet voltage."
   ::= { sBTAModulesRPCOutletEntry 7 }


sBTAModulesRPCOutletPower       OBJECT-TYPE
   SYNTAX INTEGER
   ACCESS read-only
   STATUS mandatory
   DESCRIPTION
      "The outlet power."
   ::= { sBTAModulesRPCOutletEntry 8 }


sBTAModulesRPCOutletVA          OBJECT-TYPE
   SYNTAX INTEGER
   ACCESS read-only
   STATUS mandatory
   DESCRIPTION
      "The outlet volt-amps."
   ::= { sBTAModulesRPCOutletEntry 9 }
   
sBTAModulesRPCOutletPowerFactor OBJECT-TYPE
   SYNTAX INTEGER
   ACCESS read-only
   STATUS mandatory
   DESCRIPTION
      "The outlet power factor (power/VA)."
   ::= { sBTAModulesRPCOutletEntry 10 }
   
sBTAModulesRPCOutletCurrentAlarmThreshold   OBJECT-TYPE
   SYNTAX INTEGER
   ACCESS read-write
   STATUS mandatory
   DESCRIPTION
      "The outlet current threshold for trap generation, tenths of amps"
   ::= { sBTAModulesRPCOutletEntry 11 }         
   
sBTAModulesRPCOutletPowerFactorAlarmThreshold OBJECT-TYPE
   SYNTAX INTEGER
   ACCESS read-write
   STATUS mandatory
   DESCRIPTION
      "The outlet power factor threshold for trap generation"
   ::= { sBTAModulesRPCOutletEntry 12 }     
   
sBTAModulesRPCOutletPowerFactorPowerThreshold OBJECT-TYPE
   SYNTAX INTEGER
   ACCESS read-write
   STATUS mandatory
   DESCRIPTION
      "The outlet power factor power level threshold for trap generation, watts"
   ::= { sBTAModulesRPCOutletEntry 13 }     

sBTAModulesRPCOutletKWHours OBJECT-TYPE
   SYNTAX INTEGER
   ACCESS read-write
   STATUS mandatory
   DESCRIPTION
      "The outlet kilowatt hours"
   ::= { sBTAModulesRPCOutletEntry 14 }     

sBTAModulesRPCOutletType        OBJECT-TYPE
   SYNTAX INTEGER
   ACCESS read-only
   STATUS mandatory
   DESCRIPTION
      "Outlet capabilities. Bitwise definition:
         bit 0: 0 - no relay control, 1 - relay control 
         bit 1: 0 - IEC, 1 - NEMA
         bit 2: 0 - unmetered, 1 - metered"
   ::= { sBTAModulesRPCOutletEntry 15 }

sBTAModulesRPCOutletCircuit     OBJECT-TYPE
   SYNTAX INTEGER
   ACCESS read-only
   STATUS mandatory
   DESCRIPTION
      "The circuit number the outlet is connected to."
   ::= { sBTAModulesRPCOutletEntry 16 }

   
   
sBTAModulesRPCGroupCmd OBJECT-TYPE
   SYNTAX DisplayString
   ACCESS read-write
   STATUS mandatory
   DESCRIPTION
      "A character string listing the outlets that need to be controlled,
      turned off, or turn on as a group.  Command is the first character
      followed by a space.  Valid commads are 0=off,1=on, or 2=reboot. A
      list follows the command in the format module.outlet.  For example
      2 2.1,2.12,3.1  will reboot module 2 outlet 2&12 module 3 outlet 1."
   ::= { sBTAModulesRPC 4 }


-- the sBTAModulesRPCCurrentGroup group

sBTAModulesRPCCurrentGroupsCurrentTable OBJECT-TYPE
   SYNTAX SEQUENCE OF SBTAModulesRPCCurrentGroupsCurrentEntry
   ACCESS not-accessible
   STATUS mandatory
   DESCRIPTION
    " A list of total current for RPCs in each current group"
   ::= { sBTAModulesRPC 8 }

sBTAModulesRPCCurrentGroupsCurrentEntry OBJECT-TYPE
   SYNTAX SBTAModulesRPCCurrentGroupsCurrentEntry
   ACCESS not-accessible
   STATUS mandatory
   DESCRIPTION
      "Table of total current measurement by group"
   INDEX  { groupCurrentIndex}
   ::= { sBTAModulesRPCCurrentGroupsCurrentTable 1 }

SBTAModulesRPCCurrentGroupsCurrentEntry ::=
   SEQUENCE {
      groupCurrentIndex     INTEGER,
      groupCurrent      INTEGER,
      rpcGroup          DisplayString,
      warningThreshold      INTEGER,
      emergencyThreshold    INTEGER
   }

groupCurrentIndex OBJECT-TYPE
   SYNTAX INTEGER
   ACCESS read-only
   STATUS mandatory
   DESCRIPTION
      "The index to a group total current."
   ::= { sBTAModulesRPCCurrentGroupsCurrentEntry 1 }

groupCurrent OBJECT-TYPE
   SYNTAX INTEGER
   ACCESS read-only
   STATUS mandatory
   DESCRIPTION
    "Current total for all RPCs in group."
   ::= { sBTAModulesRPCCurrentGroupsCurrentEntry 2 }

rpcGroup OBJECT-TYPE
   SYNTAX DisplayString
   ACCESS read-write
   STATUS mandatory
   DESCRIPTION
      "A character string listing the RPCs, by port index, that will be
       included in a measurement of total current.  For each group, a sum
       will be periodically computed of currents of all listed RPCs, which
       will be compared to warning and emergency thresholds, generating
       appropriate traps as required by transit of a threshold. A maximum
       of 8 RPCs may be monitored within a group.  The RPC must be connected
       and operating and the corresponding DS74 serial port must be configured
       for an RPC-SNMP device type to be allowed group membership."
   ::= { sBTAModulesRPCCurrentGroupsCurrentEntry 3 }

warningThreshold OBJECT-TYPE
   SYNTAX INTEGER
   ACCESS read-write
   STATUS mandatory
   DESCRIPTION
    "The current level, in tenths of an amp, that will cause a Current
         Level Warning trap to be sent if the total current for the associated
     group if exceeded.  Conversely, a Current Level Warning Clear trap
     will be sent whent the total group current falls below the threshold."
   ::= { sBTAModulesRPCCurrentGroupsCurrentEntry 4 }

emergencyThreshold OBJECT-TYPE
   SYNTAX INTEGER
   ACCESS read-write
   STATUS mandatory
   DESCRIPTION
    "The current level, in tenths of an amp, that will cause a Current
         Level Emergency trap to be sent if the total current for the associated
     group if exceeded.  Conversely, a Current Level Emergeny Clear trap
     will be sent whent the total group current falls below the threshold."
   ::= { sBTAModulesRPCCurrentGroupsCurrentEntry 5}


--  Individual strip table (by circuit - for RPC 28 & other multi-circuit units)

sBTAModulesRPCCircuitsTable OBJECT-TYPE
   SYNTAX SEQUENCE OF SBTAModulesRPCCircuitsEntry
   ACCESS not-accessible
   STATUS mandatory
   DESCRIPTION
      "Allows monitoring of individual outlet circuits on RPCs. "
   ::= { sBTAModulesRPC 9 }

sBTAModulesRPCCircuitsEntry OBJECT-TYPE
   SYNTAX SBTAModulesRPCCircuitsEntry
   ACCESS not-accessible
   STATUS mandatory
   DESCRIPTION
      "Status organization by circuit."
   INDEX  { sBTAModulesRPCCircuitsModuleIndex,sBTAModulesRPCCircuitsCircuitIndex}
   ::= { sBTAModulesRPCCircuitsTable 1 }

SBTAModulesRPCCircuitsEntry ::=
   SEQUENCE {
      sBTAModulesRPCCircuitsModuleIndex         INTEGER,
      sBTAModulesRPCCircuitsCircuitIndex        INTEGER,
      sBTAModulesRPCCircuitsCurrent         INTEGER,
      sBTAModulesRPCCircuitsMaxCurrent          INTEGER,
      sBTAModulesRPCCircuitsVoltage         INTEGER,
      sBTAModulesRPCCircuitsPower           INTEGER,
      sBTAModulesRPCCircuitsVA              INTEGER,
      sBTAModulesRPCCircuitsCurrentAlarmThreshold   INTEGER,
      sBTAModulesRPCircuitsPowerFactor  INTEGER,
      sBTAModulesRPCircuitsPowerFactorAlarmThreshold  INTEGER,
      sBTAModulesRPCircuitsPowerFactorPowerThreshold  INTEGER,
      sBTAModulesRPCCircuitsInputPowerSource    INTEGER
}


sBTAModulesRPCCircuitsModuleIndex OBJECT-TYPE
   SYNTAX INTEGER
   ACCESS read-only
   STATUS mandatory
   DESCRIPTION
      "The index into the power control device circuits table."
   ::= { sBTAModulesRPCCircuitsEntry 1 }

sBTAModulesRPCCircuitsCircuitIndex OBJECT-TYPE
   SYNTAX INTEGER
   ACCESS read-only
   STATUS mandatory
   DESCRIPTION
      "The index into the power control device circuits table."
   ::= { sBTAModulesRPCCircuitsEntry 2 }

sBTAModulesRPCCircuitsCurrent OBJECT-TYPE
   SYNTAX INTEGER
   ACCESS read-only
   STATUS mandatory
   DESCRIPTION
      "The detected current reading for the power strip.
       If current measurement is not installed this value will always read 0."
   ::= { sBTAModulesRPCCircuitsEntry 4 }

sBTAModulesRPCCircuitsMaxCurrent OBJECT-TYPE
   SYNTAX INTEGER
   ACCESS read-only
   STATUS mandatory
   DESCRIPTION
      "The maximum detected current reading for the power strip.
       If current measurement is not installed this value will always read 0."
   ::= { sBTAModulesRPCCircuitsEntry 5 }

sBTAModulesRPCCircuitsVoltage OBJECT-TYPE
   SYNTAX INTEGER
   ACCESS read-only
   STATUS mandatory
   DESCRIPTION
      "The voltage reading for the power strip.
       If voltage measurement is not installed this value will always read 0."
   ::= { sBTAModulesRPCCircuitsEntry 6 }

sBTAModulesRPCCircuitsPower OBJECT-TYPE
   SYNTAX INTEGER
   ACCESS read-only
   STATUS mandatory
   DESCRIPTION
      "The power reading for the power strip.
       If voltage measurement is not installed this value will always read 0."
   ::= { sBTAModulesRPCCircuitsEntry 7 }

sBTAModulesRPCCircuitsVA OBJECT-TYPE
   SYNTAX INTEGER
   ACCESS read-only
   STATUS mandatory
   DESCRIPTION
      "The volt-amps reading for the power strip.
       If voltage measurement is not installed this value will always read 0."
   ::= { sBTAModulesRPCCircuitsEntry 8 }

sBTAModulesRPCCircuitsCurrentAlarmThreshold OBJECT-TYPE
   SYNTAX INTEGER
   ACCESS read-write
   STATUS mandatory
   DESCRIPTION
      "The current alarm threshold level *10.  A value of 105 will set the level to 10.5."
   ::= { sBTAModulesRPCCircuitsEntry 9 }


sBTAModulesRPCircuitsPowerFactor OBJECT-TYPE
   SYNTAX INTEGER
   ACCESS read-only
   STATUS mandatory
   DESCRIPTION
      "The power factor for given ciruit (power/VA). "
   ::= { sBTAModulesRPCCircuitsEntry 10 }

sBTAModulesRPCircuitsPowerFactorAlarmThreshold OBJECT-TYPE
   SYNTAX INTEGER
   ACCESS read-write
   STATUS mandatory
   DESCRIPTION
      "The power factor alarm threshold level."
   ::= { sBTAModulesRPCCircuitsEntry 11 }

sBTAModulesRPCircuitsPowerFactorPowerThreshold OBJECT-TYPE
   SYNTAX INTEGER
   ACCESS read-write
   STATUS mandatory
   DESCRIPTION
      "The minimum power level for power factor alarm to be active."
   ::= { sBTAModulesRPCCircuitsEntry 12 }

sBTAModulesRPCCircuitsInputPowerSource OBJECT-TYPE
   SYNTAX INTEGER
   ACCESS read-only
   STATUS mandatory
   DESCRIPTION
      "The input power source - circuit connection. 1 for single input power
      source units, power source number for dual input source units"
   ::= { sBTAModulesRPCCircuitsEntry 13 }

-- the sBTAControl group

sBTAControlResetUnit OBJECT-TYPE
   SYNTAX INTEGER  {
   noreset (0),
   reset (1)
   }
   ACCESS read-write
   STATUS mandatory
   DESCRIPTION
      "Setting this value to 1 will cause the unit to reset.
       A get of this OID will return 0."
   ::= { sBTAControl 1 }

sBTAControlResetModules OBJECT-TYPE
   SYNTAX INTEGER  {
   noreset (0),
   reset (1)
   }
   ACCESS read-write
   STATUS mandatory
   DESCRIPTION
      "Setting this value to 1 will cause the unit to reset modules
       simular to the telnet RM command.  A get of this OID will return 0."
   ::= { sBTAControl 2 }

sBTAControlNumOfLoggedUsers OBJECT-TYPE
   SYNTAX INTEGER
   ACCESS read-only
   STATUS mandatory
   DESCRIPTION
      "Number of users logged in via telnet or SSH."
   ::= { sBTAControl 3 }

sBTAControlUserTable OBJECT-TYPE
   SYNTAX SEQUENCE OF SBTAControlUserEntry
   ACCESS not-accessible
   STATUS mandatory
   DESCRIPTION
      "A list of users and user information.
       The number of entries is contained in the sBTAControlNumOfLoggedUsers OID."
   ::= { sBTAControl 4 }

sBTAControlUserEntry OBJECT-TYPE
   SYNTAX SBTAControlUserEntry
   ACCESS not-accessible
   STATUS mandatory
   DESCRIPTION
      "The users to get status on."
   INDEX  { sBTAControlUserIndex}
   ::= { sBTAControlUserTable 1 }

SBTAControlUserEntry ::=
   SEQUENCE {
      sBTAControlUserIndex            INTEGER,
      sBTAControlUserName             DisplayString,
      sBTAControlUserAddress          IpAddress,
      sBTAControlUserConnection      INTEGER,
      sBTAControlUserConnModule       INTEGER,
      sBTAControlUserConnPort         INTEGER,
      sBTAControlUserTerminateUser   INTEGER
   }

sBTAControlUserIndex OBJECT-TYPE
   SYNTAX INTEGER
   ACCESS read-only
   STATUS mandatory
   DESCRIPTION
      "The index to the user entry."
   ::= { sBTAControlUserEntry 1 }

sBTAControlUserName    OBJECT-TYPE
   SYNTAX  DisplayString
   ACCESS  read-only
   STATUS  mandatory
   DESCRIPTION
      "The username of the user."

   ::= { sBTAControlUserEntry  2 }

sBTAControlUserAddress OBJECT-TYPE
   SYNTAX IpAddress
   ACCESS read-only
   STATUS mandatory
   DESCRIPTION
      "The IP address of the user."
   ::= { sBTAControlUserEntry 3 }

sBTAControlUserConnection OBJECT-TYPE
   SYNTAX INTEGER {
   serialport (0),
   telnet (1),
   ssh (2),
   unknown (4)
   }
   ACCESS read-only
   STATUS mandatory
   DESCRIPTION
      "Type of connection.
       If unknown, user is logging out or the connection is invalid."
   ::= { sBTAControlUserEntry 4 }

sBTAControlUserConnModule OBJECT-TYPE
   SYNTAX INTEGER
   ACCESS read-only
   STATUS mandatory
   DESCRIPTION
      "If the user is connected to a module, this value will
       report the module number connected to.
       If the value is 0 the user is not connected to a module."
   ::= { sBTAControlUserEntry 5 }

sBTAControlUserConnPort OBJECT-TYPE
   SYNTAX INTEGER
   ACCESS read-only
   STATUS mandatory
   DESCRIPTION
      "The port number with in a module that the user is connected to.
       This usually only applies to connections to DS74 serial modules.
       Intelligent modules connections are always made on port 1.
       If value is 0 the user is not connected to a module."
   ::= { sBTAControlUserEntry 6 }

sBTAControlUserTerminateUser OBJECT-TYPE
   SYNTAX INTEGER {
      terminate (1)
   }
   ACCESS read-write
   STATUS mandatory
   DESCRIPTION
      "Settings this OID to anything but 0 will terminate (log out) the user.
       A get of this OID will return 0."
   ::= { sBTAControlUserEntry 7 }

-- the sBTAFileTransfer group
sBTAFileTransferEnableUpgradeFTPFileTransfer OBJECT-TYPE
   SYNTAX INTEGER   {
      enableUpgradeFileTransferDownloadViaFTP   (1)
   }
   ACCESS read-write
  STATUS mandatory
   DESCRIPTION
      "Setting this OID to enableUpgradeFileTransferDownloadViaFTP (1)
      will start the FTP server and place the DS72 in upgrade mode. An
      FTP connection may then be established for the purpose of transmitting
      a firmware upgrade file."
   ::= { sBTAFileTransfer 1 }

-- the mtrapargs group

mtrapargsInteger OBJECT-TYPE
   SYNTAX INTEGER
   ACCESS read-only
   STATUS mandatory
   DESCRIPTION
      "This OID allows baytech traps to be sent with an integer argument
       that may not be defined in the baytech MIB.

       A get of this OID will return 0."
   ::= { mtrapargs 1 }

mtrapargsIpAddress OBJECT-TYPE
   SYNTAX IpAddress
   ACCESS read-only
   STATUS mandatory
   DESCRIPTION
      "This OID allows bayteh traps to be sent with an IP address argument
       that may not be defined in the baytech MIB.

       A get of this OID will return 0.0.0.0."
   ::= { mtrapargs 2 }

mtrapargsString OBJECT-TYPE
   SYNTAX  DisplayString
   ACCESS read-only
   STATUS mandatory
   DESCRIPTION
      "This OID allows baytech traps to be sent with an octet string argument
       that may not be defined in the baytech MIB.

       A get of this OID will return a NULL string."
   ::= { mtrapargs 3 }

mtrapargsGauge OBJECT-TYPE
   SYNTAX  Gauge
   ACCESS read-only
   STATUS mandatory
   DESCRIPTION
      "This OID allows baytech traps to be sent with a Gauge argument
       that may not be defined in the baytech MIB.

       A get of this OID will return 0."
   ::= { mtrapargs 4 }

mtrapargsTimeTicks OBJECT-TYPE
   SYNTAX TimeTicks
   ACCESS read-only
   STATUS mandatory
   DESCRIPTION
      "This OID allows baytech traps to be sent with a TimeTicks argument
       that may not be defined in the baytech MIB.

       A get of this OID will return 0."
   ::= { mtrapargs 5 }

sBTAModuleIndex OBJECT-TYPE
   SYNTAX INTEGER
   ACCESS read-only
   STATUS mandatory
   DESCRIPTION
      "This OID allows baytech traps to be sent with an integer argument
       that may not be defined in the baytech MIB.  This is an index to a specific
       DS module. Value will equal the slot of the module.

       A get of this OID will return 0."
   ::= { mtrapargs 6 }

sBTAOutletIndex OBJECT-TYPE
   SYNTAX INTEGER
   ACCESS read-only
   STATUS mandatory
   DESCRIPTION
      "This OID allows baytech traps to be sent with an integer argument
       that may not be defined in the baytech MIB.  This is an index to a specific
       outlet in a DS module.

       Value is 1 to number of outlets controlled by the ds module.  0 represents
       all outlets.

       A get of this OID will return 0."
   ::= { mtrapargs 7 }

sBTAPortIndex OBJECT-TYPE
   SYNTAX INTEGER
   ACCESS read-only
   STATUS mandatory
   DESCRIPTION
      "This OID allows baytech traps to be sent with an integer argument
       that may not be defined in the baytech MIB.  This is an index to a specific
       outlet in a DS module.

       Value is 1 to number of outlets controlled by the ds module.  0 represents
       all outlets.

       A get of this OID will return 0."
   ::= { mtrapargs 8 }

sBTAVoltageSource OBJECT-TYPE
   SYNTAX INTEGER
   ACCESS read-write
   STATUS mandatory
   DESCRIPTION
      "This OID allows baytech traps to be sent with an integer argument
       that may not be defined in the baytech MIB.  This is the number associated
       with the voltage source in an RPC.

       Value is 1 or 2, depending on which voltage source is powering the RPC.

       A get of this OID will return 0."
   ::= { mtrapargs 9 }

sBTASourceSwitchCount OBJECT-TYPE
   SYNTAX INTEGER
   ACCESS read-only
   STATUS mandatory
   DESCRIPTION
      "This OID allows baytech traps to be sent with an integer argument
       that may not be defined in the baytech MIB.  This is the number associated
       with the number of voltage source transitions in an RPC.

       Value is 0 to 255, an 8-bit w/rollover count of number of times voltage
       source has been switched from one source to another.

       A get of this OID will return 0."
   ::= { mtrapargs 10 }

sBTASensorIndex OBJECT-TYPE
   SYNTAX INTEGER
   ACCESS read-only
   STATUS mandatory
   DESCRIPTION
      "This OID allows baytech traps to be sent with an integer argument
       that may not be defined in the baytech MIB.  This is an index to a specific
       sensor in a DS module.

       Value is 1 to number of sensors controlled by the ds module.

       A get of this OID will return 0."
   ::= { mtrapargs 11 }

sBTACircuitIndex OBJECT-TYPE
   SYNTAX INTEGER
   ACCESS read-only
   STATUS mandatory
   DESCRIPTION
      "This is an object which is sent along with a trap to designate a
      circuit number pertinent to a particular trap.  This value will
      range from 1 to the total number of Circuitsinside the particular RPC.

      A get of this OID will return 0."
   ::= { mtrapargs 12 }


sBTAInputIndex OBJECT-TYPE
   SYNTAX INTEGER
   ACCESS read-only
   STATUS mandatory
   DESCRIPTION
      "This is an object which is sent along with a trap to designate an
      input phase number pertinent to a particular trap.  This value will
      range from 1 to the total number of Input Phases for the particular RPC.

      A get of this OID will return 0."
   ::= { mtrapargs 13 }




-- Module/Port MIB definitions - uncomment lines below until comment at end
-- of block prior to compiling.

sBTAModulesRPCModPortTable OBJECT-TYPE
   SYNTAX SEQUENCE OF SBTAModulesRPCModPortEntry
   ACCESS not-accessible
   STATUS mandatory
   DESCRIPTION
      "Allows for control of individual outlets and individual power control devices. The number of
       entries is contained in the sBTAModulesNumberOfRPCModules OID."
   ::= { sBTAModulesRPC 5 }

sBTAModulesRPCModPortEntry OBJECT-TYPE
   SYNTAX SBTAModulesRPCModPortEntry
   ACCESS not-accessible
   STATUS mandatory
   DESCRIPTION
      "The power control devices to control and get status on."
   INDEX  { sRPCModuleIndex,sRPCPortIndex}
   ::= { sBTAModulesRPCModPortTable 1 }

SBTAModulesRPCModPortEntry ::=
   SEQUENCE {
      sRPCModuleIndex       INTEGER,
      sRPCPortIndex     INTEGER,
      sRPCType          DisplayString,
      sRPCName          DisplayString,
      sRPCFirmwareVersion       DisplayString,
      sRPCCurrent       INTEGER,
      sRPCMaxCurrent        INTEGER,
      sRPCVoltage               INTEGER,
      sRPCPower                 INTEGER,
      sRPCTemperature       INTEGER,
      sRPCRebootTimeout     INTEGER,
      sRPCAllOutletsCmd     INTEGER,
      sRPCAllOutletsStatus  DisplayString,
      sRPCCurrentAlarmThreshold INTEGER,
      sRPCOverVoltageThreshold  INTEGER,
      sRPCUnderVoltageThreshold INTEGER,
      sRPCNumberOfOutlets   INTEGER,
      sRPCOverTempThreshold INTEGER,
      sRPCUnitVA        INTEGER,
      sRPCNumberOfCircuits  INTEGER,
    sRPCLowCurrentThreshold INTEGER,
    sRPCVoltageSource   INTEGER,
    sRPCSourceSwitchCount   INTEGER,
    sRPCNumberOfSensors INTEGER,
    sRPCKWHours INTEGER,
    sRPCNumberOfInputSources INTEGER,
    sRPCNumberOfInputPhases INTEGER,
    sRPCTempUnits   INTEGER
   }

sRPCModuleIndex OBJECT-TYPE
   SYNTAX INTEGER
   ACCESS read-only
   STATUS mandatory
   DESCRIPTION
      "The module number index into the RPC table."
   ::= { sBTAModulesRPCModPortEntry 1 }

sRPCPortIndex OBJECT-TYPE
   SYNTAX INTEGER
   ACCESS read-only
   STATUS mandatory
   DESCRIPTION
      "The port number index into the RPC table.  In the case of ds30 modules this number is always 1."
   ::= { sBTAModulesRPCModPortEntry 2 }

sRPCType OBJECT-TYPE
   SYNTAX DisplayString
   ACCESS read-only
   STATUS mandatory
   DESCRIPTION
      "Type of RPC at the module, port index."
   ::= { sBTAModulesRPCModPortEntry 3 }

sRPCName OBJECT-TYPE
   SYNTAX DisplayString
   ACCESS read-write
   STATUS mandatory
   DESCRIPTION
      "The name (unit id) of the power control device."
   ::= { sBTAModulesRPCModPortEntry 4 }

sRPCFirmwareVersion OBJECT-TYPE
   SYNTAX DisplayString
   ACCESS read-only
   STATUS mandatory
   DESCRIPTION
      "The firware version of the power control device."
   ::= { sBTAModulesRPCModPortEntry 5 }

sRPCCurrent OBJECT-TYPE
   SYNTAX INTEGER
   ACCESS read-only
   STATUS mandatory
   DESCRIPTION
      "The current reading for the power strip.
       If current measurement is not installed this value will always read 0."
   ::= { sBTAModulesRPCModPortEntry 6 }

sRPCMaxCurrent OBJECT-TYPE
   SYNTAX INTEGER
   ACCESS read-write
   STATUS mandatory
   DESCRIPTION
      "The maximum detected current reading for the power strip.
       If current measurement is not installed this value will always read 0.
       Setting this value to 0 will clear the maximum current detected."
   ::= { sBTAModulesRPCModPortEntry 7 }

sRPCVoltage OBJECT-TYPE
   SYNTAX INTEGER
   ACCESS read-only
   STATUS mandatory
   DESCRIPTION
      "The voltage reading for the power strip.
       If voltage measurement is not installed this value will always read 0."
   ::= { sBTAModulesRPCModPortEntry 8 }

sRPCPower OBJECT-TYPE
   SYNTAX INTEGER
   ACCESS read-only
   STATUS mandatory
   DESCRIPTION
      "The power reading for the power strip.
       If power measurement is not installed this value will always read 0."
   ::= { sBTAModulesRPCModPortEntry 9 }

sRPCTemperature OBJECT-TYPE
   SYNTAX INTEGER
   ACCESS read-only
   STATUS mandatory
   DESCRIPTION
      "The temperature reading for the power strip.  Readings are in degrees C.
       If temperature measurement is not installed this value will always read 0."
   ::= { sBTAModulesRPCModPortEntry 10 }

sRPCRebootTimeout OBJECT-TYPE
   SYNTAX INTEGER
   ACCESS read-write
   STATUS mandatory
   DESCRIPTION
      "The length of off time for automatic reboot sequences.
       Currently a read-only value set to the fixed reboot timeout."
   ::= { sBTAModulesRPCModPortEntry 11 }

sRPCAllOutletsCmd OBJECT-TYPE
   SYNTAX INTEGER {
        off         (0),
        on          (1),
        reboot      (2),
        lockon      (3),
        lockoff     (4),
        unlock      (5),
        unknown     (6)
   }
   ACCESS read-write
   STATUS mandatory
   DESCRIPTION
      "Turns all outlets on, off or reboot.
       0 = off
       1 = on
       2 = reboot
       3 = lockon (will lock outlets to on state)
       4 = lockoff (will lock outlets to off state)
       5 = unlock (will unlock all outlets)

       A get will return unknown (6)."
   ::= { sBTAModulesRPCModPortEntry 12 }

sRPCAllOutletsStatus OBJECT-TYPE
   SYNTAX DisplayString
   ACCESS read-only
   STATUS mandatory
   DESCRIPTION
      "Reports status of outlets in a comma deliminated string.
       0 = off
       1 = on
       2 = reboot
       3 = locked on
       4 = locked off"
   ::= { sBTAModulesRPCModPortEntry 13 }

sRPCCurrentAlarmThreshold OBJECT-TYPE
   SYNTAX INTEGER
   ACCESS read-write
   STATUS mandatory
   DESCRIPTION
      "The current alarm threshold level *10.  A value of 105 will set the level to 10.5."
   ::= { sBTAModulesRPCModPortEntry 14 }

sRPCOverVoltageThreshold OBJECT-TYPE
   SYNTAX INTEGER
   ACCESS read-write
   STATUS mandatory
   DESCRIPTION
      "The over voltage alarm threshold level *10.  A value of 105 will set the level to 10.5."
   ::= { sBTAModulesRPCModPortEntry 15 }

sRPCUnderVoltageThreshold OBJECT-TYPE
   SYNTAX INTEGER
   ACCESS read-write
   STATUS mandatory
   DESCRIPTION
      "The under voltage alarm threshold level *10.  A value of 105 will set the level to 10.5."
   ::= { sBTAModulesRPCModPortEntry 16 }
   
sRPCNumberOfOutlets OBJECT-TYPE
   SYNTAX INTEGER
   ACCESS read-only
   STATUS mandatory
   DESCRIPTION
      "Number of outlets for this RPC.
       This will be the size of outlet table for this RPC index."
   ::= { sBTAModulesRPCModPortEntry 17 }

sRPCOverTempThreshold OBJECT-TYPE
   SYNTAX INTEGER
   ACCESS read-write
   STATUS mandatory
   DESCRIPTION
      "The over temperature alarm threshold level *10.  A value of 505 will set the level to 50.5."
   ::= { sBTAModulesRPCModPortEntry 19 }

sRPCUnitVA OBJECT-TYPE
   SYNTAX INTEGER
   ACCESS read-only
   STATUS mandatory
   DESCRIPTION
      "Number of outlets for this power control device.
       This will be the size of outlet table for this power control device index."
   ::= { sBTAModulesRPCModPortEntry 20 }

sRPCNumberOfCircuits OBJECT-TYPE
   SYNTAX INTEGER
   ACCESS read-only
   STATUS mandatory
   DESCRIPTION
      "Number of Circuits for this power control device."
   ::= { sBTAModulesRPCModPortEntry 21 }


sRPCLowCurrentThreshold OBJECT-TYPE
   SYNTAX INTEGER
   ACCESS read-write
   STATUS mandatory
   DESCRIPTION
      "Low current threshold for this power control device."
   ::= { sBTAModulesRPCModPortEntry 22 }

sRPCVoltageSource OBJECT-TYPE
   SYNTAX INTEGER
   ACCESS read-write
   STATUS mandatory
   DESCRIPTION
      "Voltage source for this power control device."
   ::= { sBTAModulesRPCModPortEntry 23 }

sRPCSourceSwitchCount OBJECT-TYPE
   SYNTAX INTEGER
   ACCESS read-write
   STATUS mandatory
   DESCRIPTION
      "Voltage source switch count for this power control device."
   ::= { sBTAModulesRPCModPortEntry 24 }

sRPCNumberOfSensors OBJECT-TYPE
   SYNTAX INTEGER
   ACCESS read-only
   STATUS mandatory
   DESCRIPTION
      "Number of sensors for this power control device."
   ::= { sBTAModulesRPCModPortEntry 25 }

sRPCKWHours OBJECT-TYPE
   SYNTAX INTEGER
   ACCESS read-write
   STATUS mandatory
   DESCRIPTION
      "Kilowatt hours for this power control device.  Setting this object
      clears the value, resetting it to 0"
   ::= { sBTAModulesRPCModPortEntry 26 }

sRPCNumberOfInputSources OBJECT-TYPE
   SYNTAX INTEGER
   ACCESS read-only
   STATUS mandatory
   DESCRIPTION
      "Number of power input sources for this power control device."
   ::= { sBTAModulesRPCModPortEntry 27 }

sRPCNumberOfInputPhases OBJECT-TYPE
   SYNTAX INTEGER
   ACCESS read-only
   STATUS mandatory
   DESCRIPTION
      "Number of power input phases for this power control device.
      A return of '0' ndicates that an input sensor module is 
      not present in the unit."
   ::= { sBTAModulesRPCModPortEntry 28 }

sRPCTempUnits OBJECT-TYPE
   SYNTAX INTEGER
   ACCESS read-write
   STATUS mandatory
   DESCRIPTION
      "Celcius: 1. Farenheit: 2.  Setting one instance in table
      sets temp units for all connected devices - no mix & match"
   ::= { sBTAModulesRPCModPortEntry 29 }
   
sBTAModulesRPCModPortOutletTable OBJECT-TYPE
   SYNTAX SEQUENCE OF SBTAModulesRPCModPortOutletEntry
   ACCESS not-accessible
   STATUS mandatory
   DESCRIPTION
      "Allows for control of individual outlets. The number of
       entries is contained in the sBTAModulesRPCOutletTableSize OID."
   ::= { sBTAModulesRPC 6 }

sBTAModulesRPCModPortOutletEntry OBJECT-TYPE
   SYNTAX SBTAModulesRPCModPortOutletEntry
   ACCESS not-accessible
   STATUS mandatory
   DESCRIPTION
      "The outlets to control and get status on."
   INDEX  { sRPCOutletModuleIndex, sRPCOutletPortIndex, sRPCOutletIndex}
   ::= { sBTAModulesRPCModPortOutletTable 1 }

SBTAModulesRPCModPortOutletEntry ::=
   SEQUENCE {
      sRPCOutletModuleIndex     INTEGER,
      sRPCOutletPortIndex       INTEGER,
      sRPCOutletIndex           INTEGER,
      sRPCOutletState           INTEGER,
      sRPCOutletName            DisplayString,
      sRPCOutletCurrent         INTEGER,
      sRPCOutletMaxCurrent      INTEGER,
      sRPCOutletVoltage         INTEGER,
      sRPCOutletPower           INTEGER,
      sRPCOutletVA              INTEGER,  
      sRPCOutletPowerFactor     INTEGER,
      sRPCOutletCurrentAlarmThreshold     INTEGER,
      sRPCOutletPowerFactorAlarmThreshold   INTEGER,
      sRPCOutletPowerFactorPowerThreshold   INTEGER,
      sRPCOutletKWHours         INTEGER,
      sRPCOutletType            INTEGER,
      sRPCOutletCircuit         INTEGER
      
   }

sRPCOutletModuleIndex OBJECT-TYPE
   SYNTAX INTEGER
   ACCESS read-only
   STATUS mandatory
   DESCRIPTION
      "The module index to the outlet entry."
   ::= { sBTAModulesRPCModPortOutletEntry 1 }

sRPCOutletPortIndex OBJECT-TYPE
   SYNTAX INTEGER
   ACCESS read-only
   STATUS mandatory
   DESCRIPTION
      "The port index to the outlet entry. In the case of ds30s this number is always 1."
   ::= { sBTAModulesRPCModPortOutletEntry 2 }

sRPCOutletIndex OBJECT-TYPE
   SYNTAX INTEGER
   ACCESS read-only
   STATUS mandatory
   DESCRIPTION
      "The outlet index to the outlet entry."
   ::= { sBTAModulesRPCModPortOutletEntry 3 }

sRPCOutletState OBJECT-TYPE
   SYNTAX INTEGER {
        off (0),
        on  (1),
        reboot  (2),
        lockon  (3),
        lockoff (4),
        unlock  (5),
        unknown (6)
   }

   ACCESS read-write
   STATUS mandatory
   DESCRIPTION
       "Getting this variable will return the state of the outlet.
       Valid return states are unknown, on, off, lockon, lockoff.
       0 = off
       1 = on
       2 = reboot
       3 = lockon (outlet is on and no changes are allowed)
       4 = lockoff (outlet is off and no changes are allowed)
       5 = unlock."

   ::= { sBTAModulesRPCModPortOutletEntry 4 }


sRPCOutletName    OBJECT-TYPE
   SYNTAX  DisplayString
   ACCESS  read-write
   STATUS  mandatory
   DESCRIPTION
      "The name of the outlet. Maximum size is 16 characters."

   ::= { sBTAModulesRPCModPortOutletEntry  5 }

sRPCOutletCurrent    OBJECT-TYPE
   SYNTAX INTEGER
   ACCESS read-only
   STATUS mandatory
   DESCRIPTION
      "The outlet current (tenths of amp)."
   ::= { sBTAModulesRPCModPortOutletEntry 6 }

sRPCOutletMaxCurrent     OBJECT-TYPE
   SYNTAX INTEGER
   ACCESS read-only
   STATUS mandatory
   DESCRIPTION
      "The max outlet current (tenths of amp)."
   ::= { sBTAModulesRPCModPortOutletEntry 7 }


sRPCOutletVoltage        OBJECT-TYPE
   SYNTAX INTEGER
   ACCESS read-only
   STATUS mandatory
   DESCRIPTION
      "The outlet voltage."
   ::= { sBTAModulesRPCModPortOutletEntry 8 }


sRPCOutletPower          OBJECT-TYPE
   SYNTAX INTEGER
   ACCESS read-only
   STATUS mandatory
   DESCRIPTION
      "The outlet power (W)."
   ::= { sBTAModulesRPCModPortOutletEntry 9 }

sRPCOutletVA             OBJECT-TYPE
   SYNTAX INTEGER
   ACCESS read-only
   STATUS mandatory
   DESCRIPTION
      "The outlet volt-amps."
   ::= { sBTAModulesRPCModPortOutletEntry 10 }

sRPCOutletPowerFactor            OBJECT-TYPE
   SYNTAX INTEGER
   ACCESS read-only
   STATUS mandatory
   DESCRIPTION
      "The outlet power factor (power/VA)."
   ::= { sBTAModulesRPCModPortOutletEntry 11 }

sRPCOutletCurrentAlarmThreshold          OBJECT-TYPE
   SYNTAX INTEGER
   ACCESS read-write
   STATUS mandatory
   DESCRIPTION
      "The outlet current threshold for trap generation, tenths of amps"
   ::= { sBTAModulesRPCModPortOutletEntry 12 }

sRPCOutletPowerFactorAlarmThreshold          OBJECT-TYPE
   SYNTAX INTEGER
   ACCESS read-write
   STATUS mandatory
   DESCRIPTION
      "The outlet power factor alarm threshold for trap generation"
   ::= { sBTAModulesRPCModPortOutletEntry 13 }

sRPCOutletPowerFactorPowerThreshold          OBJECT-TYPE
   SYNTAX INTEGER
   ACCESS read-write
   STATUS mandatory
   DESCRIPTION
      "The outlet power factor power threshold"
   ::= { sBTAModulesRPCModPortOutletEntry 14 }
   
sRPCOutletKWHours            OBJECT-TYPE
   SYNTAX INTEGER
   ACCESS read-write
   STATUS mandatory
   DESCRIPTION
      "The outlet klilowatt hours"
   ::= { sBTAModulesRPCModPortOutletEntry 15 }

sRPCOutletType      OBJECT-TYPE
   SYNTAX INTEGER
   ACCESS read-only
   STATUS mandatory
   DESCRIPTION
      "Outlet capabilities. Bitwise definition:
         bit 0: 0 - no relay control, 1 - relay control 
         bit 1: 0 - IEC, 1 - NEMA
         bit 2: 0 - unmetered, 1 - metered"
   ::= { sBTAModulesRPCModPortOutletEntry 16 }

sRPCOutletCircuit       OBJECT-TYPE
   SYNTAX INTEGER
   ACCESS read-only
   STATUS mandatory
   DESCRIPTION
      "The circuit number the outlet is connected to."
   ::= { sBTAModulesRPCModPortOutletEntry 17 }

   
sBTAModulesRPCModPortGroupCmd OBJECT-TYPE
   SYNTAX DisplayString
   ACCESS read-write
   STATUS mandatory
   DESCRIPTION
      "A character string listing the outlets that need to be rebooted,
      turned off, or turn on as a group.  Command is the first character
      followed by a space.  Valid commads are 0=off,1=on, or 2=reboot. A
      list follows the command in the format module.port.outlet.  For example
      2 2.1.1,2.1.12,3.4.1  will reboot module 2 port 1 outlet 2&12 module 3 port 4 outlet 1."
   ::= { sBTAModulesRPC 7 }
   
--  Individual strip table (by circuit - for RPC 28 & other multi-circuit units)

sRPCModPortCircuitsTable OBJECT-TYPE
   SYNTAX SEQUENCE OF SRPCModPortCircuitsEntry
   ACCESS not-accessible
   STATUS mandatory
   DESCRIPTION
      "Allows monitoring of individual outlet circuits on RPCs. "
   ::= { sBTAModulesRPC 10 }

sRPCModPortCircuitsEntry OBJECT-TYPE
   SYNTAX SRPCModPortCircuitsEntry
   ACCESS not-accessible
   STATUS mandatory
   DESCRIPTION
      "Status organization by circuit."
   INDEX  { sRPCCircuitsModIndex,sRPCCircuitsPortIndex,sRPCCircuitsCircuitIndex}
   ::= { sRPCModPortCircuitsTable 1 }

SRPCModPortCircuitsEntry ::=
   SEQUENCE {
      sRPCCircuitsModIndex              INTEGER,
      sRPCCircuitsPortIndex         INTEGER,
      sRPCCircuitsCircuitIndex      INTEGER,
      sRPCCircuitsCurrent           INTEGER,
      sRPCCircuitsMaxCurrent            INTEGER,
      sRPCCircuitsVoltage           INTEGER,
      sRPCCircuitsPower             INTEGER,
      sRPCCircuitsVA                INTEGER,
      sRPCCircuitsCurrentAlarmThreshold     INTEGER,
      sRPCCircuitsPowerFactor   INTEGER,
      sRPCCircuitsPowerFactorAlarmThreshold  INTEGER,
      sRPCCircuitsPowerFactorPowerThreshold  INTEGER,
      sRPCCircuitsInputPowerSource      INTEGER
   }

sRPCCircuitsModIndex OBJECT-TYPE
   SYNTAX INTEGER
   ACCESS read-only
   STATUS mandatory
   DESCRIPTION
      "The module index into the power control device circuit table."
   ::= { sRPCModPortCircuitsEntry 1 }

sRPCCircuitsPortIndex OBJECT-TYPE
   SYNTAX INTEGER
   ACCESS read-only
   STATUS mandatory
   DESCRIPTION
      "The port index into the power control device circuit table."
   ::= { sRPCModPortCircuitsEntry 2 }

sRPCCircuitsCircuitIndex OBJECT-TYPE
   SYNTAX INTEGER
   ACCESS read-only
   STATUS mandatory
   DESCRIPTION
      "The circuit index into the power control device circuit table."
   ::= { sRPCModPortCircuitsEntry 3 }

sRPCCircuitsCurrent OBJECT-TYPE
   SYNTAX INTEGER
   ACCESS read-only
   STATUS mandatory
   DESCRIPTION
      "The detected current reading for the power circuit.
       If current measurement is not installed this value will always read 0."
   ::= { sRPCModPortCircuitsEntry 5 }

sRPCCircuitsMaxCurrent OBJECT-TYPE
   SYNTAX INTEGER
   ACCESS read-only
   STATUS mandatory
   DESCRIPTION
      "The maximum detected current reading for the power circuit.
       If current measurement is not installed this value will always read 0."
   ::= { sRPCModPortCircuitsEntry 6 }

sRPCCircuitsVoltage OBJECT-TYPE
   SYNTAX INTEGER
   ACCESS read-only
   STATUS mandatory
   DESCRIPTION
      "The voltage reading for the power circuit.
       If voltage measurement is not installed this value will always read 0."
   ::= { sRPCModPortCircuitsEntry 7 }

sRPCCircuitsPower OBJECT-TYPE
   SYNTAX INTEGER
   ACCESS read-only
   STATUS mandatory
   DESCRIPTION
      "The power reading for the power circuit.
       If voltage measurement is not installed this value will always read 0."
   ::= { sRPCModPortCircuitsEntry 8 }

sRPCCircuitsVA OBJECT-TYPE
   SYNTAX INTEGER
   ACCESS read-only
   STATUS mandatory
   DESCRIPTION
      "The volt-amps reading for the power circuit.
       If voltage measurement is not installed this value will always read 0."
   ::= { sRPCModPortCircuitsEntry 9 }

sRPCCircuitsCurrentAlarmThreshold OBJECT-TYPE
   SYNTAX INTEGER
   ACCESS read-write
   STATUS mandatory
   DESCRIPTION
      "The current alarm threshold level x10.  A value of 105 will set the level to 10.5."
   ::= { sRPCModPortCircuitsEntry 10 }

sRPCCircuitsPowerFactor  OBJECT-TYPE
   SYNTAX INTEGER
   ACCESS read-only
   STATUS mandatory
   DESCRIPTION
      "The power factor for the power circuit (power/VA). "
   ::= { sRPCModPortCircuitsEntry 11 }

sRPCCircuitsPowerFactorAlarmThreshold OBJECT-TYPE
   SYNTAX INTEGER
   ACCESS read-write
   STATUS mandatory
   DESCRIPTION
      "The power factor alarm threshold level for the power circuit"
   ::= { sRPCModPortCircuitsEntry 12 }


sRPCCircuitsPowerFactorPowerThreshold OBJECT-TYPE
   SYNTAX INTEGER
   ACCESS read-write
   STATUS mandatory
   DESCRIPTION
      "The power factor minimum power threshold level"
   ::= { sRPCModPortCircuitsEntry 13 }

sRPCCircuitsInputPowerSource OBJECT-TYPE
   SYNTAX INTEGER
   ACCESS read-only
   STATUS mandatory
   DESCRIPTION
      "The input power source - circuit connection. 1 for single input power
      source units, power source number for dual input power source units"
   ::= { sRPCModPortCircuitsEntry 14 }



sRPCOutletGroupTable OBJECT-TYPE
   SYNTAX SEQUENCE OF SRPCOutletGroupEntry
   ACCESS not-accessible
   STATUS mandatory
   DESCRIPTION
      "Allows control of outlets via a group of up to four outlets. "
   ::= { sBTAModulesRPC 11 }

sRPCOutletGroupEntry OBJECT-TYPE
   SYNTAX SRPCOutletGroupEntry
   ACCESS not-accessible
   STATUS mandatory
   DESCRIPTION
      "Organized by group number."
   INDEX  { sRPCOutletGroupIndex}
   ::= { sRPCOutletGroupTable 1 }

SRPCOutletGroupEntry ::=
   SEQUENCE {
      sRPCOutletGroupIndex      INTEGER,
      sRPCOutletGroupName       DisplayString,
      sRPCOutletGroupOutlets    DisplayString,
      sRPCOutletGroupCmd        INTEGER
   }

sRPCOutletGroupIndex OBJECT-TYPE
   SYNTAX INTEGER
   ACCESS read-only
   STATUS mandatory
   DESCRIPTION
      "The index into the outlet group table."
   ::= { sRPCOutletGroupEntry 1 }

sRPCOutletGroupName OBJECT-TYPE
   SYNTAX DisplayString
   ACCESS read-write
   STATUS mandatory
   DESCRIPTION
      "The name of the outlet group."
   ::= { sRPCOutletGroupEntry 2 }

sRPCOutletGroupOutlets OBJECT-TYPE
   SYNTAX DisplayString
   ACCESS read-write
   STATUS mandatory
   DESCRIPTION
      "The list of outlets in the outlet group.  
      Format is mod.port.outlet,mod.port.outlet up to 4 outlets."
   ::= { sRPCOutletGroupEntry 3 }

sRPCOutletGroupCmd OBJECT-TYPE
   SYNTAX INTEGER {
        off (0),
        on  (1),
        reboot  (2),
        lockon  (3),
        lockoff (4),
        unlock  (5),
        unknown (6)
   }
   ACCESS read-write
   STATUS mandatory
   DESCRIPTION
      "Command for outlet group.  Same rules as rpc commands."
   ::= { sRPCOutletGroupEntry 4 }


sBTAModulesRPCInputSourcesTable OBJECT-TYPE
   SYNTAX SEQUENCE OF SBTAModulesRPCInputSourcesEntry
   ACCESS not-accessible
   STATUS mandatory
   DESCRIPTION
      "Allows monitoring of individual input power source parameters on 
      power control/monitoring devices "
   ::= { sBTAModulesRPC 12 }

sBTAModulesRPCInputSourcesEntry OBJECT-TYPE
   SYNTAX SBTAModulesRPCInputSourcesEntry
   ACCESS not-accessible
   STATUS mandatory
   DESCRIPTION
      "Status organization by input power source."
   INDEX  { sBTAModulesRPCInputSourceModulesIndex,sBTAModulesRPCInputSourceIndex}
   ::= { sBTAModulesRPCInputSourcesTable 1 }

SBTAModulesRPCInputSourcesEntry ::=
   SEQUENCE {
      sBTAModulesRPCInputSourceModulesIndex INTEGER,
      sBTAModulesRPCInputSourceIndex        INTEGER,
      sBTAModulesRPCInputSourceCircuitsList DisplayString,
      sBTAModulesRPCInputSourceCurrent      INTEGER,
      sBTAModulesRPCInputSourceKWHours      INTEGER
}

sBTAModulesRPCInputSourceModulesIndex OBJECT-TYPE
   SYNTAX INTEGER
   ACCESS read-only
   STATUS mandatory
   DESCRIPTION
      "The module index into the input source table."
   ::= { sBTAModulesRPCInputSourcesEntry 1 }

sBTAModulesRPCInputSourceIndex OBJECT-TYPE
   SYNTAX INTEGER
   ACCESS read-only
   STATUS mandatory
   DESCRIPTION
      "The power source index into the input source table."
   ::= { sBTAModulesRPCInputSourcesEntry 2 }

sBTAModulesRPCInputSourceCircuitsList    OBJECT-TYPE
   SYNTAX  DisplayString
   ACCESS  read-only
   STATUS  mandatory
   DESCRIPTION
      "The list of circuits on the input power source."
   ::= { sBTAModulesRPCInputSourcesEntry  3 }

sBTAModulesRPCInputSourceCurrent OBJECT-TYPE
   SYNTAX INTEGER
   ACCESS read-only
   STATUS mandatory
   DESCRIPTION
      "The current for the indexed input power source."
   ::= { sBTAModulesRPCInputSourcesEntry 4 }

sBTAModulesRPCInputSourceKWHours OBJECT-TYPE
   SYNTAX INTEGER
   ACCESS read-only
   STATUS mandatory
   DESCRIPTION
      "The Kilowatt hours for the indexed input power source."
   ::= { sBTAModulesRPCInputSourcesEntry 5 }




sRPCInputSourcesTable OBJECT-TYPE
   SYNTAX SEQUENCE OF SRPCInputSourcesEntry
   ACCESS not-accessible
   STATUS mandatory
   DESCRIPTION
      "Allows monitoring of individual input power source parameters on 
      power control/monitoring devices "
   ::= { sBTAModulesRPC 13 }

sRPCInputSourcesEntry OBJECT-TYPE
   SYNTAX SRPCInputSourcesEntry
   ACCESS not-accessible
   STATUS mandatory
   DESCRIPTION
      "Status organization by input power source."
   INDEX  { sRPCInputSourceModIndex,sRPCInputSourcePortIndex,sRPCInputSourceSourceIndex}
   ::= { sRPCInputSourcesTable 1 }

SRPCInputSourcesEntry ::=
   SEQUENCE {
      sRPCInputSourceModIndex    INTEGER,
      sRPCInputSourcePortIndex  INTEGER,
      sRPCInputSourceSourceIndex    INTEGER,
      sRPCInputSourceCircuitsList   DisplayString,
      sRPCInputSourceCurrent        INTEGER,
      sRPCInputSourceKWHours        INTEGER
}

sRPCInputSourceModIndex OBJECT-TYPE
   SYNTAX INTEGER
   ACCESS read-only
   STATUS mandatory
   DESCRIPTION
      "The module index into the input source table."
   ::= { sRPCInputSourcesEntry 1 }

sRPCInputSourcePortIndex OBJECT-TYPE
   SYNTAX INTEGER
   ACCESS read-only
   STATUS mandatory
   DESCRIPTION
      "The port index into the input source table."
   ::= { sRPCInputSourcesEntry 2 }

sRPCInputSourceSourceIndex OBJECT-TYPE
   SYNTAX INTEGER
   ACCESS read-only
   STATUS mandatory
   DESCRIPTION
      "The power source index into the input source table."
   ::= { sRPCInputSourcesEntry 3 }

sRPCInputSourceCircuitsList    OBJECT-TYPE
   SYNTAX  DisplayString
   ACCESS  read-only
   STATUS  mandatory
   DESCRIPTION
      "The list of circuits on the input power source."
   ::= { sRPCInputSourcesEntry  4 }
   
sRPCInputSourceCurrent OBJECT-TYPE
   SYNTAX INTEGER
   ACCESS read-only
   STATUS mandatory
   DESCRIPTION
      "The current for the indexed input power source."
   ::= { sRPCInputSourcesEntry 5 }

sRPCInputSourceKWHours OBJECT-TYPE
   SYNTAX INTEGER
   ACCESS read-only
   STATUS mandatory
   DESCRIPTION
      "The Kilowatt hours for the indexed input power source."
   ::= { sRPCInputSourcesEntry 6 }

-- Input Tables

sBTAModulesRPCInputTable OBJECT-TYPE
   SYNTAX SEQUENCE OF SBTAModulesRPCInputEntry
   ACCESS not-accessible
   STATUS mandatory
   DESCRIPTION
      "Allows monitoring of individual voltage input parameters on 
      power control/monitoring devices "
   ::= { sBTAModulesRPC 14 }

sBTAModulesRPCInputEntry OBJECT-TYPE
   SYNTAX SBTAModulesRPCInputEntry
   ACCESS not-accessible
   STATUS mandatory
   DESCRIPTION
      "Status organization by voltage input source."
   INDEX  { sBTAModulesRPCInputModulesIndex,sBTAModulesRPCInputIndex}
   ::= { sBTAModulesRPCInputTable 1 }

SBTAModulesRPCInputEntry ::=
   SEQUENCE {
      sBTAModulesRPCInputModulesIndex   INTEGER,
      sBTAModulesRPCInputIndex          INTEGER,
      sBTAModulesRPCInputCurrent        INTEGER,
      sBTAModulesRPCInputMaxCurrent     INTEGER,
      sBTAModulesRPCInputVoltage        INTEGER,
       sBTAModulesRPCInputPower         INTEGER,
       sBTAModulesRPCInputVA            INTEGER,
     sBTAModulesRPCInputCurrentAlarmThreshold INTEGER,
    sBTAModulesRPCInputPowerFactor INTEGER,
    sBTAModulesRPCInputPowerFactorAlarmThreshold INTEGER,
    sBTAModulesRPCInputPowerFactorPowerThreshold INTEGER
}

sBTAModulesRPCInputModulesIndex OBJECT-TYPE
   SYNTAX INTEGER
   ACCESS read-only
   STATUS mandatory
   DESCRIPTION
      "The module index into the input table."
   ::= { sBTAModulesRPCInputEntry 1 }

sBTAModulesRPCInputIndex OBJECT-TYPE
   SYNTAX INTEGER
   ACCESS read-only
   STATUS mandatory
   DESCRIPTION
      "The phase index into the input table."
   ::= { sBTAModulesRPCInputEntry 2 }

sBTAModulesRPCInputCurrent OBJECT-TYPE
   SYNTAX INTEGER
   ACCESS read-only
   STATUS mandatory
   DESCRIPTION
      "The current for the indexed voltage input."
   ::= { sBTAModulesRPCInputEntry 3 }

sBTAModulesRPCInputMaxCurrent OBJECT-TYPE
   SYNTAX INTEGER
   ACCESS read-only
   STATUS mandatory
   DESCRIPTION
      "The max current for the indexed voltage input."
   ::= { sBTAModulesRPCInputEntry 4 }

sBTAModulesRPCInputVoltage OBJECT-TYPE
   SYNTAX INTEGER
   ACCESS read-only
   STATUS mandatory
   DESCRIPTION
      "The voltage for the indexed voltage input."
   ::= { sBTAModulesRPCInputEntry 5 }

sBTAModulesRPCInputPower OBJECT-TYPE
   SYNTAX INTEGER
   ACCESS read-only
   STATUS mandatory
   DESCRIPTION
      "The power for the indexed voltage input."
   ::= { sBTAModulesRPCInputEntry 6 }

sBTAModulesRPCInputVA OBJECT-TYPE
   SYNTAX INTEGER
   ACCESS read-only
   STATUS mandatory
   DESCRIPTION
      "The volt-amps for the indexed voltage input."
   ::= { sBTAModulesRPCInputEntry 7 }

sBTAModulesRPCInputCurrentAlarmThreshold OBJECT-TYPE
   SYNTAX INTEGER
   ACCESS read-write
   STATUS mandatory
   DESCRIPTION
      "The current alarm threshold for the indexed voltage input."
   ::= { sBTAModulesRPCInputEntry 8 }

sBTAModulesRPCInputPowerFactor OBJECT-TYPE
   SYNTAX INTEGER
   ACCESS read-only
   STATUS mandatory
   DESCRIPTION
      "The power factor for the input."
   ::= { sBTAModulesRPCInputEntry 9 }

sBTAModulesRPCInputPowerFactorAlarmThreshold OBJECT-TYPE
   SYNTAX INTEGER
   ACCESS read-write
   STATUS mandatory
   DESCRIPTION
      "The power factor alarm threshold level for the input"
   ::= { sBTAModulesRPCInputEntry 10 }


sBTAModulesRPCInputPowerFactorPowerThreshold OBJECT-TYPE
   SYNTAX INTEGER
   ACCESS read-write
   STATUS mandatory
   DESCRIPTION
      "The minimum power required to generate a power factor alarm for the input"
   ::= { sBTAModulesRPCInputEntry 11 }



sRPCInputTable OBJECT-TYPE
   SYNTAX SEQUENCE OF SRPCInputEntry
   ACCESS not-accessible
   STATUS mandatory
   DESCRIPTION
      "Allows monitoring of individual input power source parameters on 
      power control/monitoring devices "
   ::= { sBTAModulesRPC 15 }

sRPCInputEntry OBJECT-TYPE
   SYNTAX SRPCInputEntry
   ACCESS not-accessible
   STATUS mandatory
   DESCRIPTION
      "Status organization by input voltage source."
   INDEX  { sRPCInputModIndex,sRPCInputPortIndex,sRPCInputIndex}
   ::= { sRPCInputTable 1 }

SRPCInputEntry ::=
   SEQUENCE {
      sRPCInputModIndex  INTEGER,
      sRPCInputPortIndex    INTEGER,
      sRPCInputIndex    INTEGER,
      sRPCInputCurrent      INTEGER,
      sRPCInputMaxCurrent       INTEGER,
      sRPCInputVoltage      INTEGER,
      sRPCInputPower        INTEGER,
      sRPCInputVA       INTEGER,
      sRPCInputCurrentAlarmThreshold     INTEGER,
      sRPCInputPowerFactor  INTEGER,
      sRPCInputPowerFactorAlarmThreshold  INTEGER,
      sRPCInputPowerFactorPowerThreshold  INTEGER
}

sRPCInputModIndex OBJECT-TYPE
   SYNTAX INTEGER
   ACCESS read-only
   STATUS mandatory
   DESCRIPTION
      "The module index into the input voltage table."
   ::= { sRPCInputEntry 1 }

sRPCInputPortIndex OBJECT-TYPE
   SYNTAX INTEGER
   ACCESS read-only
   STATUS mandatory
   DESCRIPTION
      "The port index into the input voltage table."
   ::= { sRPCInputEntry 2 }

sRPCInputIndex OBJECT-TYPE
   SYNTAX INTEGER
   ACCESS read-only
   STATUS mandatory
   DESCRIPTION
      "The voltage source index into the input table."
   ::= { sRPCInputEntry 3 }

sRPCInputCurrent OBJECT-TYPE
   SYNTAX INTEGER
   ACCESS read-only
   STATUS mandatory
   DESCRIPTION
      "The current for the indexed input voltage source."
   ::= { sRPCInputEntry 4 }

sRPCInputMaxCurrent OBJECT-TYPE
   SYNTAX INTEGER
   ACCESS read-only
   STATUS mandatory
   DESCRIPTION
      "The max current for the indexed input voltage source."
   ::= { sRPCInputEntry 5 }

sRPCInputVoltage OBJECT-TYPE
   SYNTAX INTEGER
   ACCESS read-only
   STATUS mandatory
   DESCRIPTION
      "The voltage for the indexed input voltage source."
   ::= { sRPCInputEntry 6 }
 
sRPCInputPower OBJECT-TYPE
   SYNTAX INTEGER
   ACCESS read-only
   STATUS mandatory
   DESCRIPTION
      "The power for the indexed input voltage source."
   ::= { sRPCInputEntry 7 }
 
sRPCInputVA OBJECT-TYPE
   SYNTAX INTEGER
   ACCESS read-only
   STATUS mandatory
   DESCRIPTION
      "The volt-amps for the indexed input voltage source."
   ::= { sRPCInputEntry 8 }

sRPCInputCurrentAlarmThreshold OBJECT-TYPE
   SYNTAX INTEGER
   ACCESS read-write
   STATUS mandatory
   DESCRIPTION
      "The current alarm threshold for the indexed input voltage source."
   ::= { sRPCInputEntry 9 }

sRPCInputPowerFactor OBJECT-TYPE
   SYNTAX INTEGER
   ACCESS read-only
   STATUS mandatory
   DESCRIPTION
      "The power factor for the input."
   ::= { sRPCInputEntry 10 }

sRPCInputPowerFactorAlarmThreshold OBJECT-TYPE
   SYNTAX INTEGER
   ACCESS read-write
   STATUS mandatory
   DESCRIPTION
      "The power factor alarm threshold level for the input"
   ::= { sRPCInputEntry 11 }


sRPCInputPowerFactorPowerThreshold OBJECT-TYPE
   SYNTAX INTEGER
   ACCESS read-write
   STATUS mandatory
   DESCRIPTION
      "The minimum power required to generate a power factor alarm for the input"
   ::= { sRPCInputEntry 12 }

-- Redundant Power Source Tables

sBTAModulesRPCRPSTable OBJECT-TYPE
   SYNTAX SEQUENCE OF SBTAModulesRPCRPSEntry
   ACCESS not-accessible
   STATUS mandatory
   DESCRIPTION
      "Provides access to redundant power resources"
   ::= { sBTAModulesRPC 16 }

sBTAModulesRPCRPSEntry OBJECT-TYPE
   SYNTAX SBTAModulesRPCRPSEntry
   ACCESS not-accessible
   STATUS mandatory
   DESCRIPTION
      "Redundant Power Resources status & control."
   INDEX  { sBTAModulesRPCRPSIndex}
   ::= { sBTAModulesRPCRPSTable 1 }

SBTAModulesRPCRPSEntry ::=
   SEQUENCE {
      sBTAModulesRPCRPSIndex        INTEGER,
      sBTAModulesRPCRPSNumberOfPhases INTEGER,
      sBTAModulesRPCRPSSource       INTEGER,
      sBTAModulesRPCRPSSwitchCount  INTEGER,
      sBTAModulesRPCRPSS1PAVoltage  INTEGER,
      sBTAModulesRPCRPSS1PBVoltage  INTEGER,
      sBTAModulesRPCRPSS1PCVoltage  INTEGER,
      sBTAModulesRPCRPSS2PAVoltage  INTEGER,
      sBTAModulesRPCRPSS2PBVoltage  INTEGER,
      sBTAModulesRPCRPSS2PCVoltage  INTEGER
   }                           
   
sBTAModulesRPCRPSIndex OBJECT-TYPE
   SYNTAX INTEGER
   ACCESS read-only
   STATUS mandatory
   DESCRIPTION
      "The modules index into the Redundant Power Resources table."
   ::= { sBTAModulesRPCRPSEntry 1 }
   
sBTAModulesRPCRPSNumberOfPhases OBJECT-TYPE
   SYNTAX INTEGER
   ACCESS read-only
   STATUS mandatory
   DESCRIPTION
      "The Redundant Power Resources phase profile.  '1' - single phase. '3' - 3 phase"
   ::= { sBTAModulesRPCRPSEntry 2 }

sBTAModulesRPCRPSSource OBJECT-TYPE
   SYNTAX INTEGER
   ACCESS read-write
   STATUS mandatory
   DESCRIPTION
      "The Redundant Power Resources Voltage source, either '1' or '2'."
   ::= { sBTAModulesRPCRPSEntry 3 }

sBTAModulesRPCRPSSwitchCount OBJECT-TYPE
   SYNTAX INTEGER
   ACCESS read-only
   STATUS mandatory
   DESCRIPTION
      "The Redundant Power Resources Voltage source switch count."
   ::= { sBTAModulesRPCRPSEntry 4 }
   
sBTAModulesRPCRPSS1PAVoltage OBJECT-TYPE
  SYNTAX INTEGER
  ACCESS read-only
  STATUS mandatory
  DESCRIPTION
      "The Redundant Power Resources Voltage for Source 1, Phase A."
  ::= { sBTAModulesRPCRPSEntry 5 }
   
sBTAModulesRPCRPSS1PBVoltage OBJECT-TYPE
   SYNTAX INTEGER
   ACCESS read-only
   STATUS mandatory
   DESCRIPTION
      "The Redundant Power Resources Voltage for Source 1, Phase B."
   ::= { sBTAModulesRPCRPSEntry 6 }
   
sBTAModulesRPCRPSS1PCVoltage OBJECT-TYPE
   SYNTAX INTEGER
   ACCESS read-only
   STATUS mandatory
   DESCRIPTION
     "The Redundant Power Resources Voltage for Source 1, Phase C."
   ::= { sBTAModulesRPCRPSEntry 7 }
   
sBTAModulesRPCRPSS2PAVoltage OBJECT-TYPE
   SYNTAX INTEGER
   ACCESS read-only
   STATUS mandatory
   DESCRIPTION
      "The Redundant Power Resources Voltage for Source 2, Phase A."
   ::= { sBTAModulesRPCRPSEntry 8 }
   
sBTAModulesRPCRPSS2PBVoltage OBJECT-TYPE
   SYNTAX INTEGER
   ACCESS read-only
   STATUS mandatory
   DESCRIPTION
      "The Redundant Power Resources Voltage for Source 2, Phase B."
   ::= { sBTAModulesRPCRPSEntry 9 }
   
sBTAModulesRPCRPSS2PCVoltage OBJECT-TYPE
   SYNTAX INTEGER
   ACCESS read-only
   STATUS mandatory
   DESCRIPTION
      "The Redundant Power Resources Voltage for Source 2, Phase C."
   ::= { sBTAModulesRPCRPSEntry 10 }
   
   
sRPCRPSTable OBJECT-TYPE
   SYNTAX SEQUENCE OF SRPCRPSEntry
   ACCESS not-accessible
   STATUS mandatory
   DESCRIPTION
      "Provides access to redundant power resources"
   ::= { sBTAModulesRPC 17 }

sRPCRPSEntry OBJECT-TYPE
   SYNTAX SRPCRPSEntry
   ACCESS not-accessible
   STATUS mandatory
   DESCRIPTION
      "Redundant Power Resources status & control."
   INDEX  { sRPCRPSModuleIndex, sRPCRPSPortIndex}
   ::= { sRPCRPSTable 1 }

SRPCRPSEntry ::=
   SEQUENCE {
      sRPCRPSModuleIndex        INTEGER,
      sRPCRPSPortIndex      INTEGER,
      sRPCRPSNumberOfPhases INTEGER,
      sRPCRPSSource     INTEGER,
      sRPCRPSSwitchCount    INTEGER,
      sRPCRPSS1PAVoltage    INTEGER,
      sRPCRPSS1PBVoltage    INTEGER,
      sRPCRPSS1PCVoltage    INTEGER,
      sRPCRPSS2PAVoltage    INTEGER,
      sRPCRPSS2PBVoltage    INTEGER,
      sRPCRPSS2PCVoltage    INTEGER
   }                           
   
sRPCRPSModuleIndex OBJECT-TYPE
   SYNTAX INTEGER
   ACCESS read-only
   STATUS mandatory
   DESCRIPTION
      "The module index into the Redundant Power Resources table."
   ::= { sRPCRPSEntry 1 }
   
sRPCRPSPortIndex OBJECT-TYPE
   SYNTAX INTEGER
   ACCESS read-only
   STATUS mandatory
   DESCRIPTION
      "The port index into the Redundant Power Resources table."
   ::= { sRPCRPSEntry 2 }
   
sRPCRPSNumberOfPhases OBJECT-TYPE
   SYNTAX INTEGER
   ACCESS read-only
   STATUS mandatory
   DESCRIPTION
      "The Redundant Power Resources phase profile.  '1' - single phase. '3' - 3 phase"
   ::= { sRPCRPSEntry 3 }

sRPCRPSSource OBJECT-TYPE
   SYNTAX INTEGER
   ACCESS read-write
   STATUS mandatory
   DESCRIPTION
      "The Redundant Power Resources Voltage source, either '1' or '2'."
   ::= { sRPCRPSEntry 4 }

sRPCRPSSwitchCount OBJECT-TYPE
   SYNTAX INTEGER
   ACCESS read-only
   STATUS mandatory
   DESCRIPTION
      "The Redundant Power Resources Voltage source switch count."
   ::= { sRPCRPSEntry 5 }
   
sRPCRPSS1PAVoltage OBJECT-TYPE
  SYNTAX INTEGER
  ACCESS read-only
  STATUS mandatory
  DESCRIPTION
      "The Redundant Power Resources Voltage for Source 1, Phase A."
  ::= { sRPCRPSEntry 6 }
   
sRPCRPSS1PBVoltage OBJECT-TYPE
   SYNTAX INTEGER
   ACCESS read-only
   STATUS mandatory
   DESCRIPTION
      "The Redundant Power Resources Voltage for Source 1, Phase B."
   ::= { sRPCRPSEntry 7 }
   
sRPCRPSS1PCVoltage OBJECT-TYPE
   SYNTAX INTEGER
   ACCESS read-only
   STATUS mandatory
   DESCRIPTION
     "The Redundant Power Resources Voltage for Source 1, Phase C."
   ::= { sRPCRPSEntry 8 }
   
sRPCRPSS2PAVoltage OBJECT-TYPE
   SYNTAX INTEGER
   ACCESS read-only
   STATUS mandatory
   DESCRIPTION
      "The Redundant Power Resources Voltage for Source 2, Phase A."
   ::= { sRPCRPSEntry 9 }
   
sRPCRPSS2PBVoltage OBJECT-TYPE
   SYNTAX INTEGER
   ACCESS read-only
   STATUS mandatory
   DESCRIPTION
      "The Redundant Power Resources Voltage for Source 2, Phase B."
   ::= { sRPCRPSEntry 10 }
   
sRPCRPSS2PCVoltage OBJECT-TYPE
   SYNTAX INTEGER
   ACCESS read-only
   STATUS mandatory
   DESCRIPTION
      "The Redundant Power Resources Voltage for Source 2, Phase C."
   ::= { sRPCRPSEntry 11 }
   

-- 'All' Threshold Commands

sBTAAllCircuitsPowerFactorAlarmThreshold OBJECT-TYPE
   SYNTAX INTEGER
   ACCESS read-write
   STATUS mandatory
   DESCRIPTION
    "Set power factor alarm threshold for all circuits."
   ::= { sBTAModules 8 }

sBTAAllCircuitsPowerFactorPowerThreshold OBJECT-TYPE
   SYNTAX INTEGER
   ACCESS read-write
   STATUS mandatory
   DESCRIPTION
      "Set power factor minimum power threshold level for all circuits"
   ::= { sBTAModules 9 }

sBTAAllOutletsPowerFactorAlarmThreshold OBJECT-TYPE
   SYNTAX INTEGER
   ACCESS read-write
   STATUS mandatory
   DESCRIPTION
    "Set power factor alarm threshold for all outlets."
   ::= { sBTAModules 10 }

sBTAAllOutletsPowerFactorPowerThreshold OBJECT-TYPE
   SYNTAX INTEGER
   ACCESS read-write
   STATUS mandatory
   DESCRIPTION
      "Set power factor minimum power threshold level for all outlets"
   ::= { sBTAModules 11 }

-- *************************************************
-- end of BTA Modules
-- *************************************************
-- the Environmental group
sBTAModulesEnvironmentalObjectsTable OBJECT-TYPE
   SYNTAX SEQUENCE OF SBTAModulesEnvironmentalObjectsEntry
   ACCESS not-accessible
   STATUS mandatory
   DESCRIPTION
      "Allows monitoring of individual sensors on RPCs. "
   ::= { sBTAEnvironmental 1 }

sBTAModulesEnvironmentalObjectsEntry OBJECT-TYPE
   SYNTAX SBTAModulesEnvironmentalObjectsEntry
   ACCESS not-accessible
   STATUS mandatory
   DESCRIPTION
      "Status organization by sensor."
   INDEX  { sBTAModulesEnvironmentalModulesIndex, sBTAModulesEnvironmentalSensorsIndex}
   ::= { sBTAModulesEnvironmentalObjectsTable 1 }


SBTAModulesEnvironmentalObjectsEntry ::=
   SEQUENCE {
      sBTAModulesEnvironmentalModulesIndex      INTEGER,
      sBTAModulesEnvironmentalSensorsIndex      INTEGER,
      sBTAModulesEnvironmentalType      INTEGER,
      sBTAModulesEnvironmentalName      DisplayString,
      sBTAModulesEnvironmentalMeasurement   INTEGER,
      sBTAModulesEnvironmentalHiThreshold   INTEGER,
      sBTAModulesEnvironmentalLoThreshold       INTEGER,
      sBTAModulesEnvironmentalMax       INTEGER,
      sBTAModulesEnvironmentalMin       INTEGER,
      sBTAModulesEnvironmentalHiThresholdEn INTEGER,
      sBTAModulesEnvironmentalLoThresholdEn INTEGER,
      sBTAModulesEnvironmentalStateTrapEn   INTEGER
   }

sBTAModulesEnvironmentalModulesIndex OBJECT-TYPE
   SYNTAX INTEGER
   ACCESS read-only
   STATUS mandatory
   DESCRIPTION
    "Module Index for Environemntal table"
   ::= { sBTAModulesEnvironmentalObjectsEntry 1 }

sBTAModulesEnvironmentalSensorsIndex OBJECT-TYPE
   SYNTAX INTEGER
   ACCESS read-only
   STATUS mandatory
   DESCRIPTION
    "Sensor Index for Environemntal table"
   ::= { sBTAModulesEnvironmentalObjectsEntry 2 }

sBTAModulesEnvironmentalType OBJECT-TYPE
   SYNTAX INTEGER
   ACCESS read-only
   STATUS mandatory
   DESCRIPTION
   "Environmental Object Type.
    Type Description   Sensor Class 
      1   Temperature    Measurement 
      2   Contact        State
      3   Air Flow       Measurement
      4   Humidity       Measurement "
   ::= { sBTAModulesEnvironmentalObjectsEntry 3 }

sBTAModulesEnvironmentalName OBJECT-TYPE
   SYNTAX DisplayString
   ACCESS read-write
   STATUS mandatory
   DESCRIPTION
      "The name for the environmental object."
   ::= { sBTAModulesEnvironmentalObjectsEntry 4 }

sBTAModulesEnvironmentalMeasurement OBJECT-TYPE
   SYNTAX INTEGER
   ACCESS read-only
   STATUS mandatory
   DESCRIPTION
    "The measurement or state for the object."
   ::= { sBTAModulesEnvironmentalObjectsEntry 5 }

sBTAModulesEnvironmentalHiThreshold OBJECT-TYPE
   SYNTAX INTEGER
   ACCESS read-write
   STATUS mandatory
   DESCRIPTION
    "Hi threshold for object."
   ::= { sBTAModulesEnvironmentalObjectsEntry 6 }

sBTAModulesEnvironmentalLoThreshold OBJECT-TYPE
   SYNTAX INTEGER
   ACCESS read-write
   STATUS mandatory
   DESCRIPTION
    "Lo threshold for object."
   ::= { sBTAModulesEnvironmentalObjectsEntry 7 }

sBTAModulesEnvironmentalMax OBJECT-TYPE
   SYNTAX INTEGER
   ACCESS read-write
   STATUS mandatory
   DESCRIPTION
    "Max value recorded for object since last reset."
   ::= { sBTAModulesEnvironmentalObjectsEntry 8 }

sBTAModulesEnvironmentalMin OBJECT-TYPE
   SYNTAX INTEGER
   ACCESS read-write
   STATUS mandatory
   DESCRIPTION
    "Min value recorded for object since last reset."
   ::= { sBTAModulesEnvironmentalObjectsEntry 9 }

sBTAModulesEnvironmentalHiThresholdEn OBJECT-TYPE
   SYNTAX INTEGER
   ACCESS read-write
   STATUS mandatory
   DESCRIPTION
    "Hi threshold enable for object."
   ::= { sBTAModulesEnvironmentalObjectsEntry 10 }

sBTAModulesEnvironmentalLoThresholdEn OBJECT-TYPE
   SYNTAX INTEGER
   ACCESS read-write
   STATUS mandatory
   DESCRIPTION
    "Lo threshold enable for object."
   ::= { sBTAModulesEnvironmentalObjectsEntry 11 }

sBTAModulesEnvironmentalStateTrapEn OBJECT-TYPE
   SYNTAX INTEGER
   ACCESS read-write
   STATUS mandatory
   DESCRIPTION
    "Trap enable for environmental sensors with contacts."
   ::= { sBTAModulesEnvironmentalObjectsEntry 12 }



sRPCEnvironmentalObjectsTable OBJECT-TYPE
   SYNTAX SEQUENCE OF SRPCEnvironmentalObjectsEntry
   ACCESS not-accessible
   STATUS mandatory
   DESCRIPTION
      "Allows monitoring of individual outlet strips on RPCs. "
   ::= { sBTAEnvironmental 2 }

sRPCEnvironmentalObjectsEntry OBJECT-TYPE
   SYNTAX SRPCEnvironmentalObjectsEntry
   ACCESS not-accessible
   STATUS mandatory
   DESCRIPTION
      "Status organization by sensor."
   INDEX  { sRPCEnvironmentalModuleIndex, sRPCEnvironmentalPortIndex, sRPCEnvironmentalSensorsIndex}
   ::= { sRPCEnvironmentalObjectsTable 1 }


SRPCEnvironmentalObjectsEntry ::=
   SEQUENCE {
      sRPCEnvironmentalModuleIndex  INTEGER,
      sRPCEnvironmentalPortIndex    INTEGER,
      sRPCEnvironmentalSensorsIndex INTEGER,
      sRPCEnvironmentalType         INTEGER,
      sRPCEnvironmentalName         DisplayString,
      sRPCEnvironmentalMeasurement  INTEGER,
      sRPCEnvironmentalHiThreshold  INTEGER,
      sRPCEnvironmentalLoThreshold  INTEGER,
      sRPCEnvironmentalMax      INTEGER,
      sRPCEnvironmentalMin      INTEGER,
      sRPCEnvironmentalHiThresholdEn    INTEGER,
      sRPCEnvironmentalLoThresholdEn    INTEGER,
      sRPCEnvironmentalStateTrapEn  INTEGER
   }

sRPCEnvironmentalModuleIndex OBJECT-TYPE
   SYNTAX INTEGER
   ACCESS read-only
   STATUS mandatory
   DESCRIPTION
    "Module Index for Environemntal table"
   ::= { sRPCEnvironmentalObjectsEntry 1 }

sRPCEnvironmentalPortIndex OBJECT-TYPE
   SYNTAX INTEGER
   ACCESS read-only
   STATUS mandatory
   DESCRIPTION
    "Port Index for Environemntal table"
   ::= { sRPCEnvironmentalObjectsEntry 2 }

sRPCEnvironmentalSensorsIndex OBJECT-TYPE
   SYNTAX INTEGER
   ACCESS read-only
   STATUS mandatory
   DESCRIPTION
    "Sensor Index for Environemntal table"
   ::= { sRPCEnvironmentalObjectsEntry 3 }

sRPCEnvironmentalType OBJECT-TYPE
   SYNTAX INTEGER
   ACCESS read-only
   STATUS mandatory
   DESCRIPTION
    "Environmental Object Type.
    Type Description   Sensor Class 
      1   Temperature    Measurement 
      2   Contact        State
      3   Air Flow       Measurement
      4   Humidity       Measurement "
   ::= { sRPCEnvironmentalObjectsEntry 4 }

sRPCEnvironmentalName OBJECT-TYPE
   SYNTAX DisplayString
   ACCESS read-write
   STATUS mandatory
   DESCRIPTION
      "The name for the environmental object."
   ::= { sRPCEnvironmentalObjectsEntry 5 }

sRPCEnvironmentalMeasurement OBJECT-TYPE
   SYNTAX INTEGER
   ACCESS read-only
   STATUS mandatory
   DESCRIPTION
    "The measurement or state for the object."
   ::= { sRPCEnvironmentalObjectsEntry 6 }

sRPCEnvironmentalHiThreshold OBJECT-TYPE
   SYNTAX INTEGER
   ACCESS read-write
   STATUS mandatory
   DESCRIPTION
    "Hi threshold for object."
   ::= { sRPCEnvironmentalObjectsEntry 7 }

sRPCEnvironmentalLoThreshold OBJECT-TYPE
   SYNTAX INTEGER
   ACCESS read-write
   STATUS mandatory
   DESCRIPTION
    "Lo threshold for object."
   ::= { sRPCEnvironmentalObjectsEntry 8 }

sRPCEnvironmentalMax OBJECT-TYPE
   SYNTAX INTEGER
   ACCESS read-write
   STATUS mandatory
   DESCRIPTION
    "Max value recorded for object since last reset."
   ::= { sRPCEnvironmentalObjectsEntry 9 }

sRPCEnvironmentalMin OBJECT-TYPE
   SYNTAX INTEGER
   ACCESS read-write
   STATUS mandatory
   DESCRIPTION
    "Min value recorded for object since last reset."
   ::= { sRPCEnvironmentalObjectsEntry 10 }

sRPCEnvironmentalHiThresholdEn OBJECT-TYPE
   SYNTAX INTEGER
   ACCESS read-write
   STATUS mandatory
   DESCRIPTION
    "Hi threshold enable for object."
   ::= { sRPCEnvironmentalObjectsEntry 11 }

sRPCEnvironmentalLoThresholdEn OBJECT-TYPE
   SYNTAX INTEGER
   ACCESS read-write
   STATUS mandatory
   DESCRIPTION
    "Lo threshold enable for object."
   ::= { sRPCEnvironmentalObjectsEntry 12 }

sRPCEnvironmentalStateTrapEn OBJECT-TYPE
   SYNTAX INTEGER
   ACCESS read-write
   STATUS mandatory
   DESCRIPTION
    "Trap enable for environmental sensors with contacts."
   ::= { sRPCEnvironmentalObjectsEntry 13 }

sBTAEnvironmentalAllTemperatureSensorsHiThreshold OBJECT-TYPE
   SYNTAX INTEGER
   ACCESS read-write
   STATUS mandatory
   DESCRIPTION
    "Hi Threshold for all temperature sensors."
   ::= { sBTAEnvironmental 3 }

sBTAEnvironmentalAllTemperatureSensorsLoThreshold OBJECT-TYPE
   SYNTAX INTEGER
   ACCESS read-write
   STATUS mandatory
   DESCRIPTION
    "Lo Threshold for all temperature sensors."
   ::= { sBTAEnvironmental 4 }

sBTAEnvironmentalAllTemperatureSensorsHiThresholdTrapEnable OBJECT-TYPE
   SYNTAX INTEGER
   ACCESS read-write
   STATUS mandatory
   DESCRIPTION
    "Hi Threshold trap enable for all temperature sensors."
   ::= { sBTAEnvironmental 5 }

sBTAEnvironmentalAllTemperatureSensorsLoThresholdTrapEnable OBJECT-TYPE
   SYNTAX INTEGER
   ACCESS read-write
   STATUS mandatory
   DESCRIPTION
    "Lo Threshold trap enable for all temperature sensors."
   ::= { sBTAEnvironmental 6 }

sBTAEnvironmentalAllSensorsStateTrapEnable OBJECT-TYPE
   SYNTAX INTEGER
   ACCESS read-write
   STATUS mandatory
   DESCRIPTION
    "State change environmental sensor (ex: contact) trap enable."
   ::= { sBTAEnvironmental 7 }

sBTAEnvironmentalAllHumiditySensorsHiThreshold OBJECT-TYPE
   SYNTAX INTEGER
   ACCESS read-write
   STATUS mandatory
   DESCRIPTION
    "Hi Threshold for all humidity sensors."
   ::= { sBTAEnvironmental 8 }

sBTAEnvironmentalAllHumiditySensorsLoThreshold OBJECT-TYPE
   SYNTAX INTEGER
   ACCESS read-write
   STATUS mandatory
   DESCRIPTION
    "Lo Threshold for all humidity sensors."
   ::= { sBTAEnvironmental 9 }

sBTAEnvironmentalAllHumiditySensorsHiThresholdTrapEnable OBJECT-TYPE
   SYNTAX INTEGER
   ACCESS read-write
   STATUS mandatory
   DESCRIPTION
    "Hi Threshold trap enable for all humidity sensors."
   ::= { sBTAEnvironmental 10 }

sBTAEnvironmentalAllHumiditySensorsLoThresholdTrapEnable OBJECT-TYPE
   SYNTAX INTEGER
   ACCESS read-write
   STATUS mandatory
   DESCRIPTION
    "Lo Threshold trap enable for all humidity sensors."
   ::= { sBTAEnvironmental 11 }

sBTAEnvironmentalAllAirflowSensorsHiThreshold OBJECT-TYPE
   SYNTAX INTEGER
   ACCESS read-write
   STATUS mandatory
   DESCRIPTION
    "Hi Threshold for all airflow sensors."
   ::= { sBTAEnvironmental 12 }

sBTAEnvironmentalAllAirflowSensorsLoThreshold OBJECT-TYPE
   SYNTAX INTEGER
   ACCESS read-write
   STATUS mandatory
   DESCRIPTION
    "Lo Threshold for all airflow sensors."
   ::= { sBTAEnvironmental 13 }

sBTAEnvironmentalAllAirflowSensorsHiThresholdTrapEnable OBJECT-TYPE
   SYNTAX INTEGER
   ACCESS read-write
   STATUS mandatory
   DESCRIPTION
    "Hi Threshold trap enable for all airflow sensors."
   ::= { sBTAEnvironmental 14 }

sBTAEnvironmentalAllAirflowSensorsLoThresholdTrapEnable OBJECT-TYPE
   SYNTAX INTEGER
   ACCESS read-write
   STATUS mandatory
   DESCRIPTION
    "Lo Threshold trap enable for all airflow sensors."
   ::= { sBTAEnvironmental 15 }


-- the Alarms group
sBTAAlarmsTable OBJECT-TYPE
   SYNTAX SEQUENCE OF SBTAAlarmsEntry
   ACCESS not-accessible
   STATUS mandatory
   DESCRIPTION
      "Table of alarms issued by unit. "
   ::= { sBTAAlarms 1 }

sBTAAlarmsEntry OBJECT-TYPE
   SYNTAX SBTAAlarmsEntry
   ACCESS not-accessible
   STATUS mandatory
   DESCRIPTION
      "List of active alarms."
   INDEX  { sBTAAlarmsIndex}
   ::= { sBTAAlarmsTable 1 }


SBTAAlarmsEntry ::=
   SEQUENCE  {
      sBTAAlarmsIndex       INTEGER,
      sBTAAlarmsModule      INTEGER,
      sBTAAlarmsPort    INTEGER,
      sBTAAlarmsEquipmentLevel  DisplayString,
      sBTAAlarmsEquipmentInstance   INTEGER,
      sBTAAlarmsAlarmType       DisplayString,
      sBTAAlarmsAlarmState      DisplayString,
      sBTAAlarmsEquipmentReading    INTEGER
    }

sBTAAlarmsIndex OBJECT-TYPE
   SYNTAX INTEGER
   ACCESS read-only
   STATUS mandatory
   DESCRIPTION
    "The alarm index number."
   ::= { sBTAAlarmsEntry 1 }

sBTAAlarmsModule OBJECT-TYPE
   SYNTAX INTEGER
   ACCESS read-only
   STATUS mandatory
   DESCRIPTION
    "The alarm module number."
   ::= { sBTAAlarmsEntry 2 }
   
sBTAAlarmsPort OBJECT-TYPE
   SYNTAX INTEGER
   ACCESS read-only
   STATUS mandatory
   DESCRIPTION
    "The alarm port number."
   ::= { sBTAAlarmsEntry 3 }

sBTAAlarmsEquipmentLevel OBJECT-TYPE
   SYNTAX DisplayString
   ACCESS read-only
   STATUS mandatory
   DESCRIPTION
      "The hardware level generating the alarm: unit, 
      input, circuit,outlet,sensor,group."
   ::= { sBTAAlarmsEntry 4 }

sBTAAlarmsEquipmentInstance OBJECT-TYPE
   SYNTAX INTEGER
   ACCESS read-only
   STATUS mandatory
   DESCRIPTION
    "The index of the hardware, ex: outlet 20,
    circuit 2, etc."
   ::= { sBTAAlarmsEntry 5 }

sBTAAlarmsAlarmType OBJECT-TYPE
   SYNTAX DisplayString
   ACCESS read-only
   STATUS mandatory
   DESCRIPTION
      "The alarm type: current,voltage,power factor,
      temperature, humidity, contact."
   ::= { sBTAAlarmsEntry 6 }

sBTAAlarmsAlarmState OBJECT-TYPE
   SYNTAX DisplayString
   ACCESS read-only
   STATUS mandatory
   DESCRIPTION
      "The alarm state: hi,lo, warn, open, closed."
   ::= { sBTAAlarmsEntry 7 }

sBTAAlarmsEquipmentReading OBJECT-TYPE
   SYNTAX INTEGER
   ACCESS read-only
   STATUS mandatory
   DESCRIPTION
    "The measurement value of the paramter that
    caused generation of the alarm."
   ::= { sBTAAlarmsEntry 8 }

--  end of Module/Port MIB definitions


-- Traps
-- Annotations are provided for Novell's NMS product

communicationLost TRAP-TYPE
   ENTERPRISE baytech
   VARIABLES { mtrapargsTimeTicks }
   DESCRIPTION
       "SEVERE: Communication to the unit has been lost.  Steps
        to reestablish communication are in progress. Argument is timeTicks
        when communication was lost."
   --#TYPE "baytech: State change."
   --#SUMMARY "The unit has lost communications."
   --#SEVERITY SEVERE
   --#TIMEINDEX 1
   --#HELP ""
   --#HELPTAG 0
   --#STATE OPERATIONAL
   ::= 1

communicationEstablished TRAP-TYPE
   ENTERPRISE baytech
   VARIABLES { mtrapargsString }
   DESCRIPTION
      "INFORMATION: Communication with the unit has been established.
       Argument is timeTicks when communication was established."
   --#TYPE "baytech: State change."
   --#SUMMARY "The unit has established communications."
   --#SEVERITY INFORMATION
   --#TIMEINDEX 1
   --#HELP ""
   --#HELPTAG 0
   --#STATE OPERATIONAL
   ::= 2

outletOn TRAP-TYPE
   ENTERPRISE baytech
   VARIABLES { sBTAModuleIndex, sBTAOutletIndex }
   DESCRIPTION
       "WARNING: The specified RPC outlet has turned on.
       If sBTAOutletIndex equals zero, then all outlets have turned on."
   --#TYPE "baytech: State change."
   --#SUMMARY "The specifed outlet is being rebooted."
   --#SEVERITY WARNING
   --#TIMEINDEX 1
   --#HELP ""
   --#HELPTAG 0
   --#STATE OPERATIONAL
   ::= 3

outletOff TRAP-TYPE
   ENTERPRISE baytech
   VARIABLES { sBTAModuleIndex, sBTAOutletIndex }
   DESCRIPTION
       "WARNING: The specified RPC outlet has turned off.
       If sBTAOutletIndex equals zero, then all outlets have turned off."
   --#TYPE "baytech: State change."
   --#SUMMARY "The specifed outlet is now on."
   --#SEVERITY WARNING
   --#TIMEINDEX 1
   --#HELP ""
   --#HELPTAG 0
   --#STATE OPERATIONAL
   ::= 4

outletReboot TRAP-TYPE
   ENTERPRISE baytech
   VARIABLES { sBTAModuleIndex, sBTAOutletIndex }
   DESCRIPTION
       "WARNING: The specified RPC outlet has rebooted.
       If sBTAOutletIndex equals zero, then all outlets have rebooted."
   --#TYPE "baytech: State change."
   --#SUMMARY "The specifed outlet is now off."
   --#SEVERITY WARNING
   --#TIMEINDEX 1
   --#HELP ""
   --#HELPTAG 0
   --#STATE OPERATIONAL
   ::= 5

outletLocked TRAP-TYPE
   ENTERPRISE baytech
   VARIABLES { sBTAModuleIndex, sBTAOutletIndex }
   DESCRIPTION
       "WARNING: The specified RPC outlet has been locked.
       If sBTAOutletIndex equals zero, then all outlets have been locked."
   --#TYPE "baytech: State change."
   --#SUMMARY "The specifed outlet has been locked."
   --#SEVERITY WARNING
   --#TIMEINDEX 1
   --#HELP ""
   --#HELPTAG 0
   --#STATE OPERATIONAL
   ::= 6

outletUnlocked TRAP-TYPE
   ENTERPRISE baytech
   VARIABLES { sBTAModuleIndex, sBTAOutletIndex }
   DESCRIPTION
       "WARNING: The specified RPC outlet has been unlocked.
       If sBTAOutletIndex equals zero, then all outlets have been unlocked."
   --#TYPE "baytech: State change."
   --#SUMMARY "The specifed outlet has been unlocked."
   --#SEVERITY WARNING
   --#TIMEINDEX 1
   --#HELP ""
   --#HELPTAG 0
   --#STATE OPERATIONAL
   ::= 7

configChangeSNMP TRAP-TYPE
   ENTERPRISE baytech
   DESCRIPTION
       "WARNING: The SNMP configuration has been changed."
   --#TYPE "baytech: State change."
   --#SUMMARY "The SNMP configuration has been changed."
   --#SEVERITY WARNING
   --#TIMEINDEX 1
   --#HELP ""
   --#HELPTAG 0
   --#STATE OPERATIONAL
   ::= 8

configChangeOutlet TRAP-TYPE
   ENTERPRISE baytech
   VARIABLES { sBTAModuleIndex, sBTAOutletIndex }
   DESCRIPTION
       "WARNING: The specified outlet has changed configuration."
   --#TYPE "baytech: State change."
   --#SUMMARY "An outlet configuration has been changed."
   --#SEVERITY WARNING
   --#TIMEINDEX 1
   --#HELP ""
   --#HELPTAG 0
   --#STATE OPERATIONAL
   ::= 9

accessViolationConsole TRAP-TYPE
   ENTERPRISE baytech
   VARIABLES { mtrapargsString }
   DESCRIPTION
       "WARNING: Someone has attempted to login via the console with the incorrect password."
   --#TYPE "baytech: Access violation."
   --#SUMMARY "Three unsuccessful logins have been attempted."
   --#SEVERITY WARNING
   --#TIMEINDEX 1
   --#HELP ""
   --#HELPTAG 0
   --#STATE OPERATIONAL
   ::= 10

accessViolationNetwork TRAP-TYPE
   ENTERPRISE baytech
   VARIABLES { mtrapargsString }
   DESCRIPTION
       "WARNING: Someone has attempted to login via the network with the incorrect password."
   --#TYPE "baytech: Access violation."
   --#SUMMARY "Three unsuccessful logins have been attempted."
   --#SEVERITY WARNING
   --#TIMEINDEX 1
   --#HELP ""
   --#HELPTAG 0
   --#STATE OPERATIONAL
   ::= 11

userPasswordChange TRAP-TYPE
   ENTERPRISE baytech
   VARIABLES { mtrapargsString }
   DESCRIPTION
       "WARNING: The password for the specified user has been changed."
   --#TYPE "baytech: Password change."
   --#SUMMARY "Someone has changed the password for the specified user."
   --#SEVERITY WARNING
   --#TIMEINDEX 1
   --#HELP ""
   --#HELPTAG 0
   --#STATE OPERATIONAL
   ::= 12

userAdded TRAP-TYPE
   ENTERPRISE baytech
   VARIABLES { mtrapargsString }
   DESCRIPTION
       "WARNING: The specified user has been added."
   --#TYPE "baytech: Username change."
   --#SUMMARY "Someone has added the specified user."
   --#SEVERITY WARNING
   --#TIMEINDEX 1
   --#HELP ""
   --#HELPTAG 0
   --#STATE OPERATIONAL
   ::= 13

userLoggedIn TRAP-TYPE
   ENTERPRISE baytech
   VARIABLES { mtrapargsString }
   DESCRIPTION
       "INFORMATIONAL: The specified user has logged in.  "
   --#TYPE "baytech: User logged in."
   --#SUMMARY "Someone has logged in as the specified user."
   --#SEVERITY INFORMATIONAL
   --#TIMEINDEX 1
   --#HELP ""
   --#HELPTAG 0
   --#STATE OPERATIONAL
   ::= 14

temperatureThresholdViolation TRAP-TYPE
   ENTERPRISE baytech
   VARIABLES { mtrapargsInteger }
   DESCRIPTION
      "WARNING: A temperature threshold has been violated.  The argument is the rpc index."
   --#TYPE "baytech: Alarm."
   --#SUMMARY "A temperature threshold has been violated."
   --#SEVERITY WARNING
   --#TIMEINDEX 1
   --#HELP ""
   --#HELPTAG 0
   --#STATE OPERATIONAL
   ::= 15

temperatureThresholdViolationCleared TRAP-TYPE
   ENTERPRISE baytech
   VARIABLES { mtrapargsInteger }
   DESCRIPTION
      "INFORMATIONAL: A temperature threshold violated has been cleared.  The argument is the rpc index."
   --#TYPE "baytech: Alarm."
   --#SUMMARY "A temperature threshold violation has been cleared."
   --#SEVERITY INFORMATIONAL
   --#TIMEINDEX 1
   --#HELP ""
   --#HELPTAG 0
   --#STATE OPERATIONAL
   ::= 16

currentThresholdViolation TRAP-TYPE
   ENTERPRISE baytech
   VARIABLES { mtrapargsInteger }
   DESCRIPTION
      "WARNING: The preset current threshold has been violated.  The argument is the 
      remote power device index."
   --#TYPE "baytech: Alarm."
   --#SUMMARY "A current threshold has been violated."
   --#SEVERITY WARNING
   --#TIMEINDEX 1
   --#HELP ""
   --#HELPTAG 0
   --#STATE OPERATIONAL
   ::= 17

currentThresholdViolationCleared TRAP-TYPE
   ENTERPRISE baytech
   VARIABLES { mtrapargsString }
   DESCRIPTION
      "INFORMATIONAL: A current threshold violation has been cleared.  The argument is the 
      remote power device index."
   --#TYPE "baytech: Alarm."
   --#SUMMARY "A current threshold violation has been cleared."
   --#SEVERITY INFORMATIONAL
   --#TIMEINDEX 1
   --#HELP ""
   --#HELPTAG 0
   --#STATE OPERATIONAL
   ::= 18

resetModulesEvent TRAP-TYPE
   ENTERPRISE baytech
   VARIABLES { mtrapargsString }
   DESCRIPTION
      "WARNING: A reset modules (RM) command has been executed."
   --#TYPE "baytech: Reset alert."
   --#SUMMARY "Sent when a reset modules command is executed."
   --#SEVERITY WARNING
   --#TIMEINDEX 1
   --#HELP ""
   --#HELPTAG 0
   --#STATE OPERATIONAL
   ::= 19

resetModulesComplete TRAP-TYPE
   ENTERPRISE baytech
   VARIABLES { mtrapargsString }
   DESCRIPTION
      "WARNING: A reset modules (RM) command has been completed."
   --#TYPE "baytech: Reset alert."
   --#SUMMARY "The reset module command is complete."
   --#SEVERITY WARNING
   --#TIMEINDEX 1
   --#HELP ""
   --#HELPTAG 0
   --#STATE OPERATIONAL
   ::= 20

errorExecutingSNMPCommand TRAP-TYPE
   ENTERPRISE baytech
   VARIABLES { mtrapargsString }
   DESCRIPTION
      "WARNING: unable to execute SNMP command.  String contains reason and command."
   --#TYPE "baytech: Error."
   --#SUMMARY "Unable to execute SNMP command."
   --#SEVERITY WARNING
   --#TIMEINDEX 1
   --#HELP ""
   --#HELPTAG 0
   --#STATE OPERATIONAL
   ::= 21

fileTransferComplete TRAP-TYPE
   ENTERPRISE baytech
   DESCRIPTION
      "INFORMATIONAL: file transfer to unit complete."
   --#TYPE "baytech: file transfer."
   --#SUMMARY "The file transer is complete."
   --#SEVERITY INFORMATIONAL
   --#TIMEINDEX 1
   --#HELP ""
   --#HELPTAG 0
   --#STATE OPERATIONAL
   ::= 22

userTerminated TRAP-TYPE
   ENTERPRISE baytech
   VARIABLES { mtrapargsInteger }
   DESCRIPTION
      "WARNING: user terminated. Argument specifies user."
   --#TYPE "baytech: user terminated."
   --#SUMMARY "User terminated."
   --#SEVERITY WARNING
   --#TIMEINDEX 1
   --#HELP ""
   --#HELPTAG 0
   --#STATE OPERATIONAL
   ::= 23

voltageOverThresholdViolation TRAP-TYPE
   ENTERPRISE baytech
   VARIABLES { mtrapargsInteger }
   DESCRIPTION
      "WARNING: Over voltage. Argument specifies rpc."
   --#TYPE "baytech: over voltage."
   --#SUMMARY "Over voltage."
   --#SEVERITY WARNING
   --#TIMEINDEX 1
   --#HELP ""
   --#HELPTAG 0
   --#STATE OPERATIONAL
   ::= 24

voltageOverThresholdViolationCleared TRAP-TYPE
   ENTERPRISE baytech
   VARIABLES { mtrapargsInteger }
   DESCRIPTION
      "INFORMATIONAL: Over voltage cleared. Argument specifies rpc."
   --#TYPE "baytech: over voltage cleared."
   --#SUMMARY "Over voltage cleared."
   --#SEVERITY INFORMATIONAL
   --#TIMEINDEX 1
   --#HELP ""
   --#HELPTAG 0
   --#STATE OPERATIONAL
   ::= 25

voltageUnderThresholdViolation TRAP-TYPE
   ENTERPRISE baytech
   VARIABLES { sBTAModuleIndex, sBTACircuitIndex }
   DESCRIPTION
      "WARNING: Under voltage. Argument specifies power control device."
   --#TYPE "baytech: under voltage."
   --#SUMMARY "Under voltage."
   --#SEVERITY WARNING
   --#TIMEINDEX 1
   --#HELP ""
   --#HELPTAG 0
   --#STATE OPERATIONAL
   ::= 26

voltageUnderThresholdViolationCleared TRAP-TYPE
   ENTERPRISE baytech
   VARIABLES { mtrapargsInteger }
   DESCRIPTION
      "INFORMATIONAL: Under voltage cleared. Argument specifies remote power device."
   --#TYPE "baytech: under voltage cleared."
   --#SUMMARY "Under voltage cleared."
   --#SEVERITY INFORMATIONAL
   --#TIMEINDEX 1
   --#HELP ""
   --#HELPTAG 0
   --#STATE OPERATIONAL
   ::= 27

circuitAlarm TRAP-TYPE
   ENTERPRISE baytech
   VARIABLES { mtrapargsInteger }
   DESCRIPTION
      "WARNING: Circuit is open. Argument specifies power control device."
   --#TYPE "baytech: circuit."
   --#SUMMARY "circuit."
   --#SEVERITY WARNING
   --#TIMEINDEX 1
   --#HELP ""
   --#HELPTAG 0
   --#STATE OPERATIONAL
   ::= 28

rpcFailureAlarm TRAP-TYPE
   ENTERPRISE baytech
   VARIABLES { mtrapargsInteger }
   DESCRIPTION
      "WARNING: Unable to communicate to a remote power device.  Argument specifies 
      port number of power control device."
   --#TYPE "baytech: module failure."
   --#SUMMARY "Remote power device failure."
   --#SEVERITY WARNING
   --#TIMEINDEX 1
   --#HELP ""
   --#HELPTAG 0
   --#STATE OPERATIONAL
   ::= 29

userDeleted TRAP-TYPE
   ENTERPRISE baytech
   VARIABLES { mtrapargsString }
   DESCRIPTION
       "INFORMATIONAL: The specified user has logged in.  "
   --#TYPE "baytech: User logged in."
   --#SUMMARY "Someone has logged in as the specified user."
   --#SEVERITY INFORMATIONAL
   --#TIMEINDEX 1
   --#HELP ""
   --#HELPTAG 0
   --#STATE OPERATIONAL
   ::= 30

warningThresholdViolation TRAP-TYPE
   ENTERPRISE baytech
   VARIABLES { mtrapargsInteger }
   DESCRIPTION
       " "
   --#TYPE "baytech: warning alarm"
   --#SUMMARY "group current exceeds warning threshold"
   --#SEVERITY WARNING
   --#TIMEINDEX 1
   --#HELP ""
   --#HELPTAG 0
   --#STATE OPERATIONAL
   ::= 31

warningThresholdViolationClear TRAP-TYPE
   ENTERPRISE baytech
   VARIABLES { mtrapargsInteger }
   DESCRIPTION
       " "
   --#TYPE "baytech: warning alarm cleared"
   --#SUMMARY "group current has dropped below warning threshold"
   --#SEVERITY WARNING
   --#TIMEINDEX 1
   --#HELP ""
   --#HELPTAG 0
   --#STATE OPERATIONAL
   ::= 32

emergencyThresholdViolation TRAP-TYPE
   ENTERPRISE baytech
   VARIABLES { mtrapargsInteger }
   DESCRIPTION
       " "
   --#TYPE "baytech: emergency alarm"
   --#SUMMARY "group current exceeds emergency threshold"
   --#SEVERITY WARNING
   --#TIMEINDEX 1
   --#HELP ""
   --#HELPTAG 0
   --#STATE OPERATIONAL
   ::= 33

emergencyThresholdViolationClear TRAP-TYPE
   ENTERPRISE baytech
   VARIABLES { mtrapargsInteger }
   DESCRIPTION
       " "
   --#TYPE "baytech: emergency alarm cleared"
   --#SUMMARY "group current has dropped below emergency threshold"
   --#SEVERITY WARNING
   --#TIMEINDEX 1
   --#HELP ""
   --#HELPTAG 0
   --#STATE OPERATIONAL
   ::= 34

circuitAlarmClearTrap TRAP-TYPE
   ENTERPRISE baytech
   VARIABLES { mtrapargsInteger }
   DESCRIPTION
      "Circuit has been restored. Argument specifies remote power device."
   --#TYPE "baytech: circuit."
   --#SUMMARY "circuit restored."
   --#SEVERITY WARNING
   --#TIMEINDEX 1
   --#HELP ""
   --#HELPTAG 0
   --#STATE OPERATIONAL
   ::= 35

currentUnderThresholdViolation TRAP-TYPE
   ENTERPRISE baytech
   VARIABLES { mtrapargsInteger }
   DESCRIPTION
      "WARNING: Low current. Argument specifies remote power device."
   --#TYPE "baytech: low current."
   --#SUMMARY "Low current."
   --#SEVERITY WARNING
   --#TIMEINDEX 1
   --#HELP ""
   --#HELPTAG 0
   --#STATE OPERATIONAL
   ::= 36

currentUnderThresholdViolationCleared TRAP-TYPE
   ENTERPRISE baytech
   VARIABLES { mtrapargsInteger }
   DESCRIPTION
      "INFORMATIONAL: Low  current cleared. Argument specifies remote power device."
   --#TYPE "baytech: low current cleared."
   --#SUMMARY "Low current cleared."
   --#SEVERITY INFORMATIONAL
   --#TIMEINDEX 1
   --#HELP ""
   --#HELPTAG 0
   --#STATE OPERATIONAL
   ::= 37

voltageSourceChangeAlarm TRAP-TYPE
   ENTERPRISE baytech
   VARIABLES { sBTAModuleIndex, sBTAVoltageSource,sBTASourceSwitchCount }
   DESCRIPTION
      "WARNING: RPC voltage source has changed. Arguments specify modules index, 
      current voltage source, and count of number of times source has been switched."
   --#TYPE "baytech: voltage source change."
   --#SUMMARY "voltage source change."
   --#SEVERITY WARNING
   --#TIMEINDEX 1
   --#HELP ""
   --#HELPTAG 0
   --#STATE OPERATIONAL
   ::= 38

sensorTempThreshHiAlarmTrap TRAP-TYPE
   ENTERPRISE baytech
   VARIABLES { sBTAModuleIndex, sBTASensorIndex }
   DESCRIPTION
      "WARNING: Hi threshold exceeded. Arguments specify module, sensor number"
   --#TYPE "baytech. Hi temperature threshold alarm"
   --#SUMMARY "Hi temperature threshold alarm"
   --#SEVERITY WARNING
   --#TIMEINDEX 1
   --#HELP ""
   --#HELPTAG 0
   --#STATE OPERATIONAL
   ::= 39

sensorTempThreshHiAlarmClearedTrap TRAP-TYPE
   ENTERPRISE baytech
   VARIABLES { sBTAModuleIndex, sBTASensorIndex }
   DESCRIPTION
      "WARNING: Hi threshold alarm cleared. Arguments specify module, sensor number"
   --#TYPE "baytech. Hi threshold alarm cleared"
   --#SUMMARY "Hi sensor threshold alarm cleared"
   --#SEVERITY WARNING
   --#TIMEINDEX 1
   --#HELP ""
   --#HELPTAG 0
   --#STATE OPERATIONAL
   ::= 40

sensorTempThreshLoAlarmTrap TRAP-TYPE
   ENTERPRISE baytech
   VARIABLES { sBTAModuleIndex, sBTASensorIndex }
   DESCRIPTION
      "WARNING: Lo threshold alarm set. Arguments specify module, sensor number"
   --#TYPE "baytech. Lo temperature threshold alarm"
   --#SUMMARY "Lo temperature threshold alarm"
   --#SEVERITY WARNING
   --#TIMEINDEX 1
   --#HELP ""
   --#HELPTAG 0
   --#STATE OPERATIONAL
   ::= 41

sensorTempThreshLoAlarmClearedTrap TRAP-TYPE
   ENTERPRISE baytech
   VARIABLES { sBTAModuleIndex, sBTASensorIndex }
   DESCRIPTION
      "WARNING: Lo threshold alarm cleared. Arguments specify module, sensor number"
   --#TYPE "baytech. Lo temperature threshold alarm cleared"
   --#SUMMARY "Lo temperature threshold alarm cleared"
   --#SEVERITY WARNING
   --#TIMEINDEX 1
   --#HELP ""
   --#HELPTAG 0
   --#STATE OPERATIONAL
   ::= 42

sensorStateChangeTrap TRAP-TYPE
   ENTERPRISE baytech
   VARIABLES { sBTAModuleIndex, sBTASensorIndex }
   DESCRIPTION
      "WARNING: Sensor state (contact, detector, etc) has changed. Arguments specify module, sensor number"
   --#TYPE "baytech. Sensor state has changed"
   --#SUMMARY "Sensor state has changed"
   --#SEVERITY WARNING
   --#TIMEINDEX 1
   --#HELP ""
   --#HELPTAG 0
   --#STATE OPERATIONAL
   ::= 43

configChangeSensor TRAP-TYPE
   ENTERPRISE baytech
   VARIABLES { sBTAModuleIndex, sBTASensorIndex }
   DESCRIPTION
       "WARNING: The specified environmental sensor has changed configuration."
   --#TYPE "baytech: State change."
   --#SUMMARY "A sensor configuration has been changed."
   --#SEVERITY WARNING
   --#TIMEINDEX 1
   --#HELP ""
   --#HELPTAG 0
   --#STATE OPERATIONAL
   ::= 44

sensorTypeChange TRAP-TYPE
   ENTERPRISE baytech
   VARIABLES { sBTAModuleIndex, sBTASensorIndex }
   DESCRIPTION
       "WARNING: The specified environmental sensor is now a different type."
   --#TYPE "baytech: Type change."
   --#SUMMARY "A sensor type has been changed."
   --#SEVERITY WARNING
   --#TIMEINDEX 1
   --#HELP ""
   --#HELPTAG 0
   --#STATE OPERATIONAL
   ::= 45

outletCurrentThresholdViolation TRAP-TYPE
   ENTERPRISE baytech
   VARIABLES { sBTAModuleIndex, sBTAOutletIndex }
   DESCRIPTION
      "INFORMATIONAL: A current threshold violation has been cleared.  Arguments specify
      the remote power device index and outlet number."
   --#TYPE "baytech: Current Alarm."
   --#SUMMARY "A current threshold has been violated."
   --#SEVERITY WARNING
   --#TIMEINDEX 1
   --#HELP ""
   --#HELPTAG 0
   --#STATE OPERATIONAL
   ::= 46

outletCurrentThresholdViolationCleared TRAP-TYPE
   ENTERPRISE baytech
   VARIABLES { sBTAModuleIndex, sBTAOutletIndex }
   DESCRIPTION
      "INFORMATIONAL: A current threshold violation has been cleared.  Arguments specify
      the remote power device index and outlet number."
   --#TYPE "baytech: Current Alarm."
   --#SUMMARY "A current threshold violation has been cleared."
   --#SEVERITY INFORMATIONAL
   --#TIMEINDEX 1
   --#HELP ""
   --#HELPTAG 0
   --#STATE OPERATIONAL
   ::= 47

circuitPowerFactorThresholdWarning TRAP-TYPE
   ENTERPRISE baytech
   VARIABLES { sBTAModuleIndex, sBTACircuitIndex }
   DESCRIPTION
       "WARNING: The specified circuit has dropped below required Power Factor."
   --#TYPE "baytech: circuit power factor threshold violation."
   --#SUMMARY "power/VA Power Factor below threshold "
   --#SEVERITY WARNING
   --#TIMEINDEX 1
   --#HELP ""
   --#HELPTAG 0
   --#STATE OPERATIONAL
   ::= 48
 
circuitPowerFactorThresholdWarningCleared TRAP-TYPE
   ENTERPRISE baytech
   VARIABLES { sBTAModuleIndex, sBTACircuitIndex }
   DESCRIPTION
       "The specified circuit has returned to required Power Factor."
   --#TYPE "baytech: circuit power factor threshold violation cleared."
   --#SUMMARY "power/VA Power Factor at or above threshold "
   --#SEVERITY WARNING
   --#TIMEINDEX 1
   --#HELP ""
   --#HELPTAG 0
   --#STATE OPERATIONAL
   ::= 49

outletPowerFactorThresholdWarning TRAP-TYPE
   ENTERPRISE baytech
   VARIABLES { sBTAModuleIndex, sBTAOutletIndex }
   DESCRIPTION
       "WARNING: The specified circuit has dropped below required Power Factor."
   --#TYPE "baytech: outlet power factor threshold violation."
   --#SUMMARY "outlet power/VA Power Factor below threshold "
   --#SEVERITY WARNING
   --#TIMEINDEX 1
   --#HELP ""
   --#HELPTAG 0
   --#STATE OPERATIONAL
   ::= 50
 
 outletPowerFactorThresholdWarningCleared TRAP-TYPE
   ENTERPRISE baytech
   VARIABLES { sBTAModuleIndex, sBTAOutletIndex }
   DESCRIPTION
       "The specified circuit has returned to required Power Factor."
   --#TYPE "baytech: outlet power factor threshold violation cleared."
   --#SUMMARY "outlet power/VA Power Factor at or above threshold "
   --#SEVERITY WARNING
   --#TIMEINDEX 1
   --#HELP ""
   --#HELPTAG 0
   --#STATE OPERATIONAL
   ::= 51

inputCurrentThresholdViolation TRAP-TYPE
   ENTERPRISE baytech
   VARIABLES { sBTAModuleIndex, sBTAInputIndex }
   DESCRIPTION
      "INFORMATIONAL: A current threshold violation has been cleared.  Arguments specify
      the remote power device index and input number."
   --#TYPE "baytech: Input Current Alarm."
   --#SUMMARY "A current threshold has been violated."
   --#SEVERITY WARNING
   --#TIMEINDEX 1
   --#HELP ""
   --#HELPTAG 0
   --#STATE OPERATIONAL
   ::= 52

inputCurrentThresholdViolationCleared TRAP-TYPE
   ENTERPRISE baytech
   VARIABLES { sBTAModuleIndex, sBTAInputIndex }
   DESCRIPTION
      "INFORMATIONAL: A current threshold violation has been cleared.  Arguments specify
      the remote power device index and input number."
   --#TYPE "baytech: Input Current Alarm."
   --#SUMMARY "A current threshold violation has been cleared."
   --#SEVERITY INFORMATIONAL
   --#TIMEINDEX 1
   --#HELP ""
   --#HELPTAG 0
   --#STATE OPERATIONAL
   ::= 53

inputPowerFactorThresholdWarning TRAP-TYPE
   ENTERPRISE baytech
   VARIABLES { sBTAModuleIndex, sBTAInputIndex }
   DESCRIPTION
       "WARNING: The specified circuit has dropped below required Power Factor."
   --#TYPE "baytech: input power factor threshold violation."
   --#SUMMARY "input power/VA Power Factor below threshold "
   --#SEVERITY WARNING
   --#TIMEINDEX 1
   --#HELP ""
   --#HELPTAG 0
   --#STATE OPERATIONAL
   ::= 54
 
inputPowerFactorThresholdWarningCleared TRAP-TYPE
   ENTERPRISE baytech
   VARIABLES { sBTAModuleIndex, sBTAInputIndex }
   DESCRIPTION
       "The specified circuit has returned to required Power Factor."
   --#TYPE "baytech: input power factor threshold violation cleared."
   --#SUMMARY "input power/VA Power Factor at or above threshold "
   --#SEVERITY WARNING
   --#TIMEINDEX 1
   --#HELP ""
   --#HELPTAG 0
   --#STATE OPERATIONAL
   ::= 55
   
sourceVoltageOverThresholdViolation TRAP-TYPE
   ENTERPRISE baytech
   VARIABLES { sBTAModuleIndex, sBTAVoltageSource }
   DESCRIPTION
      "WARNING: Over voltage. Argument specifies voltage source number."
   --#TYPE "baytech: over voltage."
   --#SUMMARY "Over voltage."
   --#SEVERITY WARNING
   --#TIMEINDEX 1
   --#HELP ""
   --#HELPTAG 0
   --#STATE OPERATIONAL
   ::= 56

sourceVoltageOverThresholdViolationCleared TRAP-TYPE
   ENTERPRISE baytech
   VARIABLES { sBTAModuleIndex, sBTAVoltageSource }
   DESCRIPTION
      "INFORMATIONAL: Over voltage cleared. Argument specifies voltage source number."
   --#TYPE "baytech: over voltage cleared."
   --#SUMMARY "Over voltage cleared."
   --#SEVERITY INFORMATIONAL
   --#TIMEINDEX 1
   --#HELP ""
   --#HELPTAG 0
   --#STATE OPERATIONAL
   ::= 57

sourceVoltageUnderThresholdViolation TRAP-TYPE
   ENTERPRISE baytech
   VARIABLES { sBTAModuleIndex, sBTAVoltageSource }
   DESCRIPTION
      "WARNING: Under voltage. Argument specifies voltage source number."
   --#TYPE "baytech: under voltage."
   --#SUMMARY "Under voltage."
   --#SEVERITY WARNING
   --#TIMEINDEX 1
   --#HELP ""
   --#HELPTAG 0
   --#STATE OPERATIONAL
   ::= 58

sourceVoltageUnderThresholdViolationCleared TRAP-TYPE
   ENTERPRISE baytech
   VARIABLES {sBTAModuleIndex, sBTAVoltageSource }
   DESCRIPTION
      "INFORMATIONAL: Under voltage cleared. Argument specifies voltage source number."
   --#TYPE "baytech: under voltage cleared."
   --#SUMMARY "Under voltage cleared."
   --#SEVERITY INFORMATIONAL
   --#TIMEINDEX 1
   --#HELP ""
   --#HELPTAG 0
   --#STATE OPERATIONAL
   ::= 59

communicationLost NOTIFICATION-TYPE
   OBJECTS { mtrapargsTimeTicks }
   STATUS current   
   DESCRIPTION
       "SEVERE: Communication to the unit has been lost.  Steps
        to reestablish communication are in progress. Argument is timeTicks
        when communication was lost."
   --#TYPE "baytech: State change."
   --#SUMMARY "The unit has lost communications."
   --#SEVERITY SEVERE
   --#TIMEINDEX 1
   --#HELP ""
   --#HELPTAG 0
   --#STATE OPERATIONAL
   ::= { v2Notifications 1}

communicationEstablished NOTIFICATION-TYPE
   OBJECTS { mtrapargsString }
   STATUS current   
   DESCRIPTION
      "INFORMATION: Communication with the unit has been established.
       Argument is timeTicks when communication was established."
   --#TYPE "baytech: State change."
   --#SUMMARY "The unit has established communications."
   --#SEVERITY INFORMATION
   --#TIMEINDEX 1
   --#HELP ""
   --#HELPTAG 0
   --#STATE OPERATIONAL
   ::= { v2Notifications 2}

outletOn NOTIFICATION-TYPE
   OBJECTS { sBTAModuleIndex, sBTAOutletIndex }
   STATUS current   
   DESCRIPTION
       "WARNING: The specified RPC outlet has turned on.
       If sBTAOutletIndex equals zero, then all outlets have turned on."
   --#TYPE "baytech: State change."
   --#SUMMARY "The specifed outlet is being rebooted."
   --#SEVERITY WARNING
   --#TIMEINDEX 1
   --#HELP ""
   --#HELPTAG 0
   --#STATE OPERATIONAL
   ::= { v2Notifications 3}

outletOff NOTIFICATION-TYPE
   OBJECTS { sBTAModuleIndex, sBTAOutletIndex }
   STATUS current   
   DESCRIPTION
       "WARNING: The specified RPC outlet has turned off.
       If sBTAOutletIndex equals zero, then all outlets have turned off."
   --#TYPE "baytech: State change."
   --#SUMMARY "The specifed outlet is now on."
   --#SEVERITY WARNING
   --#TIMEINDEX 1
   --#HELP ""
   --#HELPTAG 0
   --#STATE OPERATIONAL
   ::= { v2Notifications 4}

outletReboot NOTIFICATION-TYPE
   OBJECTS { sBTAModuleIndex, sBTAOutletIndex }
   STATUS current   
   DESCRIPTION
       "WARNING: The specified RPC outlet has rebooted.
       If sBTAOutletIndex equals zero, then all outlets have rebooted."
   --#TYPE "baytech: State change."
   --#SUMMARY "The specifed outlet is now off."
   --#SEVERITY WARNING
   --#TIMEINDEX 1
   --#HELP ""
   --#HELPTAG 0
   --#STATE OPERATIONAL
   ::= { v2Notifications 5}

outletLocked NOTIFICATION-TYPE
   OBJECTS { sBTAModuleIndex, sBTAOutletIndex }
   STATUS current
   DESCRIPTION
       "WARNING: The specified RPC outlet has been locked.
       If sBTAOutletIndex equals zero, then all outlets have been locked."
   --#TYPE "baytech: State change."
   --#SUMMARY "The specifed outlet has been locked."
   --#SEVERITY WARNING
   --#TIMEINDEX 1
   --#HELP ""
   --#HELPTAG 0
   --#STATE OPERATIONAL
   ::= { v2Notifications 6}

outletUnlocked NOTIFICATION-TYPE
   OBJECTS { sBTAModuleIndex, sBTAOutletIndex }
   STATUS current
   DESCRIPTION
       "WARNING: The specified RPC outlet has been unlocked.
       If sBTAOutletIndex equals zero, then all outlets have been unlocked."
   --#TYPE "baytech: State change."
   --#SUMMARY "The specifed outlet has been unlocked."
   --#SEVERITY WARNING
   --#TIMEINDEX 1
   --#HELP ""
   --#HELPTAG 0
   --#STATE OPERATIONAL
   ::= { v2Notifications 7}

configChangeSNMP NOTIFICATION-TYPE
   STATUS current
   DESCRIPTION
       "WARNING: The SNMP configuration has been changed."
   --#TYPE "baytech: State change."
   --#SUMMARY "The SNMP configuration has been changed."
   --#SEVERITY WARNING
   --#TIMEINDEX 1
   --#HELP ""
   --#HELPTAG 0
   --#STATE OPERATIONAL
   ::= { v2Notifications 8}

configChangeOutlet NOTIFICATION-TYPE
   OBJECTS { sBTAModuleIndex, sBTAOutletIndex }
   STATUS current
   DESCRIPTION
       "WARNING: The specified outlet has changed configuration."
   --#TYPE "baytech: State change."
   --#SUMMARY "An outlet configuration has been changed."
   --#SEVERITY WARNING
   --#TIMEINDEX 1
   --#HELP ""
   --#HELPTAG 0
   --#STATE OPERATIONAL
   ::= { v2Notifications 9}

accessViolationConsole NOTIFICATION-TYPE
   OBJECTS { mtrapargsString }
   STATUS current
   DESCRIPTION
       "WARNING: Someone has attempted to login via the console with the incorrect password."
   --#TYPE "baytech: Access violation."
   --#SUMMARY "Three unsuccessful logins have been attempted."
   --#SEVERITY WARNING
   --#TIMEINDEX 1
   --#HELP ""
   --#HELPTAG 0
   --#STATE OPERATIONAL
   ::= { v2Notifications 10}

accessViolationNetwork NOTIFICATION-TYPE
   OBJECTS { mtrapargsString }
   STATUS current
   DESCRIPTION
       "WARNING: Someone has attempted to login via the network with the incorrect password."
   --#TYPE "baytech: Access violation."
   --#SUMMARY "Three unsuccessful logins have been attempted."
   --#SEVERITY WARNING
   --#TIMEINDEX 1
   --#HELP ""
   --#HELPTAG 0
   --#STATE OPERATIONAL
   ::= { v2Notifications 11}

userPasswordChange NOTIFICATION-TYPE
   OBJECTS { mtrapargsString }
   STATUS current
   DESCRIPTION
       "WARNING: The password for the specified user has been changed."
   --#TYPE "baytech: Password change."
   --#SUMMARY "Someone has changed the password for the specified user."
   --#SEVERITY WARNING
   --#TIMEINDEX 1
   --#HELP ""
   --#HELPTAG 0
   --#STATE OPERATIONAL
   ::= { v2Notifications 12}

userAdded NOTIFICATION-TYPE
   OBJECTS { mtrapargsString }
   STATUS current
   DESCRIPTION
       "WARNING: The specified user has been added."
   --#TYPE "baytech: Username change."
   --#SUMMARY "Someone has added the specified user."
   --#SEVERITY WARNING
   --#TIMEINDEX 1
   --#HELP ""
   --#HELPTAG 0
   --#STATE OPERATIONAL
   ::= { v2Notifications 13}

userLoggedIn NOTIFICATION-TYPE
   OBJECTS { mtrapargsString }
   STATUS current
   DESCRIPTION
       "INFORMATIONAL: The specified user has logged in.  "
   --#TYPE "baytech: User logged in."
   --#SUMMARY "Someone has logged in as the specified user."
   --#SEVERITY INFORMATIONAL
   --#TIMEINDEX 1
   --#HELP ""
   --#HELPTAG 0
   --#STATE OPERATIONAL
   ::= { v2Notifications 14}

temperatureThresholdViolation NOTIFICATION-TYPE
   OBJECTS { mtrapargsInteger }
   STATUS current
   DESCRIPTION
      "WARNING: A temperature threshold has been violated.  The argument is the rpc index."
   --#TYPE "baytech: Alarm."
   --#SUMMARY "A temperature threshold has been violated."
   --#SEVERITY WARNING
   --#TIMEINDEX 1
   --#HELP ""
   --#HELPTAG 0
   --#STATE OPERATIONAL
   ::= { v2Notifications 15}

temperatureThresholdViolationCleared NOTIFICATION-TYPE
   OBJECTS { mtrapargsInteger }
   STATUS current
   DESCRIPTION
      "INFORMATIONAL: A temperature threshold violated has been cleared.  The argument is the rpc index."
   --#TYPE "baytech: Alarm."
   --#SUMMARY "A temperature threshold violation has been cleared."
   --#SEVERITY INFORMATIONAL
   --#TIMEINDEX 1
   --#HELP ""
   --#HELPTAG 0
   --#STATE OPERATIONAL
   ::= { v2Notifications 16}

currentThresholdViolation NOTIFICATION-TYPE
   OBJECTS { mtrapargsInteger }
   STATUS current
   DESCRIPTION
      "WARNING: The preset current threshold has been violated.  The argument is the 
      remote power device index."
   --#TYPE "baytech: Alarm."
   --#SUMMARY "A current threshold has been violated."
   --#SEVERITY WARNING
   --#TIMEINDEX 1
   --#HELP ""
   --#HELPTAG 0
   --#STATE OPERATIONAL
   ::= { v2Notifications 17}

currentThresholdViolationCleared NOTIFICATION-TYPE
   OBJECTS { mtrapargsString }
   STATUS current
   DESCRIPTION
      "INFORMATIONAL: A current threshold violation has been cleared.  The argument is the 
      remote power device index."
   --#TYPE "baytech: Alarm."
   --#SUMMARY "A current threshold violation has been cleared."
   --#SEVERITY INFORMATIONAL
   --#TIMEINDEX 1
   --#HELP ""
   --#HELPTAG 0
   --#STATE OPERATIONAL
   ::= { v2Notifications 18}

resetModulesEvent NOTIFICATION-TYPE
   OBJECTS { mtrapargsString }
   STATUS current
   DESCRIPTION
      "WARNING: A reset modules (RM) command has been executed."
   --#TYPE "baytech: Reset alert."
   --#SUMMARY "Sent when a reset modules command is executed."
   --#SEVERITY WARNING
   --#TIMEINDEX 1
   --#HELP ""
   --#HELPTAG 0
   --#STATE OPERATIONAL
   ::= { v2Notifications 19}

resetModulesComplete NOTIFICATION-TYPE
   OBJECTS { mtrapargsString }
   STATUS current
   DESCRIPTION
      "WARNING: A reset modules (RM) command has been completed."
   --#TYPE "baytech: Reset alert."
   --#SUMMARY "The reset module command is complete."
   --#SEVERITY WARNING
   --#TIMEINDEX 1
   --#HELP ""
   --#HELPTAG 0
   --#STATE OPERATIONAL
   ::= { v2Notifications 20}

errorExecutingSNMPCommand NOTIFICATION-TYPE
   OBJECTS { mtrapargsString }
   STATUS current
   DESCRIPTION
      "WARNING: unable to execute SNMP command.  String contains reason and command."
   --#TYPE "baytech: Error."
   --#SUMMARY "Unable to execute SNMP command."
   --#SEVERITY WARNING
   --#TIMEINDEX 1
   --#HELP ""
   --#HELPTAG 0
   --#STATE OPERATIONAL
   ::= { v2Notifications 21}

fileTransferComplete NOTIFICATION-TYPE
   STATUS current
   DESCRIPTION
      "INFORMATIONAL: file transfer to unit complete."
   --#TYPE "baytech: file transfer."
   --#SUMMARY "The file transer is complete."
   --#SEVERITY INFORMATIONAL
   --#TIMEINDEX 1
   --#HELP ""
   --#HELPTAG 0
   --#STATE OPERATIONAL
   ::= { v2Notifications 22}

userTerminated NOTIFICATION-TYPE
   OBJECTS { mtrapargsInteger }
   STATUS current
   DESCRIPTION
      "WARNING: user terminated. Argument specifies user."
   --#TYPE "baytech: user terminated."
   --#SUMMARY "User terminated."
   --#SEVERITY WARNING
   --#TIMEINDEX 1
   --#HELP ""
   --#HELPTAG 0
   --#STATE OPERATIONAL
   ::= { v2Notifications 23}

voltageOverThresholdViolation NOTIFICATION-TYPE
   OBJECTS { mtrapargsInteger }
   STATUS current
   DESCRIPTION
      "WARNING: Over voltage. Argument specifies rpc."
   --#TYPE "baytech: over voltage."
   --#SUMMARY "Over voltage."
   --#SEVERITY WARNING
   --#TIMEINDEX 1
   --#HELP ""
   --#HELPTAG 0
   --#STATE OPERATIONAL
   ::= { v2Notifications 24}

voltageOverThresholdViolationCleared NOTIFICATION-TYPE
   OBJECTS { mtrapargsInteger }
   STATUS current
   DESCRIPTION
      "INFORMATIONAL: Over voltage cleared. Argument specifies rpc."
   --#TYPE "baytech: over voltage cleared."
   --#SUMMARY "Over voltage cleared."
   --#SEVERITY INFORMATIONAL
   --#TIMEINDEX 1
   --#HELP ""
   --#HELPTAG 0
   --#STATE OPERATIONAL
   ::= { v2Notifications 25}

voltageUnderThresholdViolation NOTIFICATION-TYPE
   OBJECTS { sBTAModuleIndex, sBTACircuitIndex }
   STATUS current
   DESCRIPTION
      "WARNING: Under voltage. Argument specifies power control device."
   --#TYPE "baytech: under voltage."
   --#SUMMARY "Under voltage."
   --#SEVERITY WARNING
   --#TIMEINDEX 1
   --#HELP ""
   --#HELPTAG 0
   --#STATE OPERATIONAL
   ::= { v2Notifications 26}

voltageUnderThresholdViolationCleared NOTIFICATION-TYPE
   OBJECTS { mtrapargsInteger }
   STATUS current
   DESCRIPTION
      "INFORMATIONAL: Under voltage cleared. Argument specifies remote power device."
   --#TYPE "baytech: under voltage cleared."
   --#SUMMARY "Under voltage cleared."
   --#SEVERITY INFORMATIONAL
   --#TIMEINDEX 1
   --#HELP ""
   --#HELPTAG 0
   --#STATE OPERATIONAL
   ::= { v2Notifications 27}

circuitAlarm NOTIFICATION-TYPE
   OBJECTS { mtrapargsInteger }
   STATUS current
   DESCRIPTION
      "WARNING: Circuit is open. Argument specifies power control device."
   --#TYPE "baytech: circuit."
   --#SUMMARY "circuit."
   --#SEVERITY WARNING
   --#TIMEINDEX 1
   --#HELP ""
   --#HELPTAG 0
   --#STATE OPERATIONAL
   ::= { v2Notifications 28}

rpcFailureAlarm NOTIFICATION-TYPE
   OBJECTS { mtrapargsInteger }
   STATUS current
   DESCRIPTION
      "WARNING: Unable to communicate to a remote power device.  Argument specifies 
      port number of power control device."
   --#TYPE "baytech: module failure."
   --#SUMMARY "Remote power device failure."
   --#SEVERITY WARNING
   --#TIMEINDEX 1
   --#HELP ""
   --#HELPTAG 0
   --#STATE OPERATIONAL
   ::= { v2Notifications 29}

userDeleted NOTIFICATION-TYPE
   OBJECTS { mtrapargsString }
   STATUS current
   DESCRIPTION
       "INFORMATIONAL: The specified user has logged in.  "
   --#TYPE "baytech: User logged in."
   --#SUMMARY "Someone has logged in as the specified user."
   --#SEVERITY INFORMATIONAL
   --#TIMEINDEX 1
   --#HELP ""
   --#HELPTAG 0
   --#STATE OPERATIONAL
   ::= { v2Notifications 30}

warningThresholdViolation NOTIFICATION-TYPE
   OBJECTS { mtrapargsInteger }
   STATUS current
   DESCRIPTION
       " "
   --#TYPE "baytech: warning alarm"
   --#SUMMARY "group current exceeds warning threshold"
   --#SEVERITY WARNING
   --#TIMEINDEX 1
   --#HELP ""
   --#HELPTAG 0
   --#STATE OPERATIONAL
   ::= { v2Notifications 31}

warningThresholdViolationClear NOTIFICATION-TYPE
   OBJECTS { mtrapargsInteger }
   STATUS current
   DESCRIPTION
       " "
   --#TYPE "baytech: warning alarm cleared"
   --#SUMMARY "group current has dropped below warning threshold"
   --#SEVERITY WARNING
   --#TIMEINDEX 1
   --#HELP ""
   --#HELPTAG 0
   --#STATE OPERATIONAL
   ::= { v2Notifications 32}

emergencyThresholdViolation NOTIFICATION-TYPE
   OBJECTS { mtrapargsInteger }
   STATUS current
   DESCRIPTION
       " "
   --#TYPE "baytech: emergency alarm"
   --#SUMMARY "group current exceeds emergency threshold"
   --#SEVERITY WARNING
   --#TIMEINDEX 1
   --#HELP ""
   --#HELPTAG 0
   --#STATE OPERATIONAL
   ::= { v2Notifications 33}

emergencyThresholdViolationClear NOTIFICATION-TYPE
   OBJECTS { mtrapargsInteger }
   STATUS current
   DESCRIPTION
       " "
   --#TYPE "baytech: emergency alarm cleared"
   --#SUMMARY "group current has dropped below emergency threshold"
   --#SEVERITY WARNING
   --#TIMEINDEX 1
   --#HELP ""
   --#HELPTAG 0
   --#STATE OPERATIONAL
   ::= { v2Notifications 34}

circuitAlarmClearTrap NOTIFICATION-TYPE
   OBJECTS { mtrapargsInteger }
   STATUS current
   DESCRIPTION
      "Circuit has been restored. Argument specifies remote power device."
   --#TYPE "baytech: circuit."
   --#SUMMARY "circuit restored."
   --#SEVERITY WARNING
   --#TIMEINDEX 1
   --#HELP ""
   --#HELPTAG 0
   --#STATE OPERATIONAL
   ::= { v2Notifications 35}

currentUnderThresholdViolation NOTIFICATION-TYPE
   OBJECTS { mtrapargsInteger }
   STATUS current
   DESCRIPTION
      "WARNING: Low current. Argument specifies remote power device."
   --#TYPE "baytech: low current."
   --#SUMMARY "Low current."
   --#SEVERITY WARNING
   --#TIMEINDEX 1
   --#HELP ""
   --#HELPTAG 0
   --#STATE OPERATIONAL
   ::= { v2Notifications 36}

currentUnderThresholdViolationCleared NOTIFICATION-TYPE
   OBJECTS { mtrapargsInteger }
   STATUS current
   DESCRIPTION
      "INFORMATIONAL: Low  current cleared. Argument specifies remote power device."
   --#TYPE "baytech: low current cleared."
   --#SUMMARY "Low current cleared."
   --#SEVERITY INFORMATIONAL
   --#TIMEINDEX 1
   --#HELP ""
   --#HELPTAG 0
   --#STATE OPERATIONAL
   ::= { v2Notifications 37}

voltageSourceChangeAlarm NOTIFICATION-TYPE
   OBJECTS { sBTAModuleIndex, sBTAVoltageSource,sBTASourceSwitchCount }
   STATUS current
   DESCRIPTION
      "WARNING: RPC voltage source has changed. Arguments specify modules index, 
      current voltage source, and count of number of times source has been switched."
   --#TYPE "baytech: voltage source change."
   --#SUMMARY "voltage source change."
   --#SEVERITY WARNING
   --#TIMEINDEX 1
   --#HELP ""
   --#HELPTAG 0
   --#STATE OPERATIONAL
   ::= { v2Notifications 38}

sensorTempThreshHiAlarmTrap NOTIFICATION-TYPE
   OBJECTS { sBTAModuleIndex, sBTASensorIndex }
   STATUS current
   DESCRIPTION
      "WARNING: Hi threshold exceeded. Arguments specify module, sensor number"
   --#TYPE "baytech. Hi temperature threshold alarm"
   --#SUMMARY "Hi temperature threshold alarm"
   --#SEVERITY WARNING
   --#TIMEINDEX 1
   --#HELP ""
   --#HELPTAG 0
   --#STATE OPERATIONAL
   ::= { v2Notifications 39}

sensorTempThreshHiAlarmClearedTrap NOTIFICATION-TYPE
   OBJECTS { sBTAModuleIndex, sBTASensorIndex }
   STATUS current
   DESCRIPTION
      "WARNING: Hi threshold alarm cleared. Arguments specify module, sensor number"
   --#TYPE "baytech. Hi threshold alarm cleared"
   --#SUMMARY "Hi sensor threshold alarm cleared"
   --#SEVERITY WARNING
   --#TIMEINDEX 1
   --#HELP ""
   --#HELPTAG 0
   --#STATE OPERATIONAL
   ::= { v2Notifications 40}
   
sensorTempThreshLoAlarmTrap NOTIFICATION-TYPE
   OBJECTS { sBTAModuleIndex, sBTASensorIndex }
   STATUS current
   DESCRIPTION
      "WARNING: Lo threshold alarm set. Arguments specify module, sensor number"
   --#TYPE "baytech. Lo temperature threshold alarm"
   --#SUMMARY "Lo temperature threshold alarm"
   --#SEVERITY WARNING
   --#TIMEINDEX 1
   --#HELP ""
   --#HELPTAG 0
   --#STATE OPERATIONAL
   ::= { v2Notifications 41}

sensorTempThreshLoAlarmClearedTrap NOTIFICATION-TYPE
   OBJECTS { sBTAModuleIndex, sBTASensorIndex }
   STATUS current
   DESCRIPTION
      "WARNING: Lo threshold alarm cleared. Arguments specify module, sensor number"
   --#TYPE "baytech. Lo temperature threshold alarm cleared"
   --#SUMMARY "Lo temperature threshold alarm cleared"
   --#SEVERITY WARNING
   --#TIMEINDEX 1
   --#HELP ""
   --#HELPTAG 0
   --#STATE OPERATIONAL
   ::= { v2Notifications 42}

sensorStateChangeTrap NOTIFICATION-TYPE
   OBJECTS { sBTAModuleIndex, sBTASensorIndex }
   STATUS current
   DESCRIPTION
      "WARNING: Sensor state (contact, detector, etc) has changed. Arguments specify module, sensor number"
   --#TYPE "baytech. Sensor state has changed"
   --#SUMMARY "Sensor state has changed"
   --#SEVERITY WARNING
   --#TIMEINDEX 1
   --#HELP ""
   --#HELPTAG 0
   --#STATE OPERATIONAL
   ::= { v2Notifications 43}

configChangeSensor NOTIFICATION-TYPE
   OBJECTS { sBTAModuleIndex, sBTASensorIndex }
   STATUS current
   DESCRIPTION
       "WARNING: The specified environmental sensor has changed configuration."
   --#TYPE "baytech: State change."
   --#SUMMARY "A sensor configuration has been changed."
   --#SEVERITY WARNING
   --#TIMEINDEX 1
   --#HELP ""
   --#HELPTAG 0
   --#STATE OPERATIONAL
   ::= { v2Notifications 44}

sensorTypeChange NOTIFICATION-TYPE
   OBJECTS { sBTAModuleIndex, sBTASensorIndex }
   STATUS current
   DESCRIPTION
       "WARNING: The specified environmental sensor is now a different type."
   --#TYPE "baytech: Type change."
   --#SUMMARY "A sensor type has been changed."
   --#SEVERITY WARNING
   --#TIMEINDEX 1
   --#HELP ""
   --#HELPTAG 0
   --#STATE OPERATIONAL
   ::= { v2Notifications 45}

outletCurrentThresholdViolation NOTIFICATION-TYPE
   OBJECTS { sBTAModuleIndex, sBTAOutletIndex }
   STATUS current
   DESCRIPTION
      "INFORMATIONAL: A current threshold violation has been cleared.  Arguments specify
      the remote power device index and outlet number."
   --#TYPE "baytech: Current Alarm."
   --#SUMMARY "A current threshold has been violated."
   --#SEVERITY WARNING
   --#TIMEINDEX 1
   --#HELP ""
   --#HELPTAG 0
   --#STATE OPERATIONAL
   ::= { v2Notifications 46}

outletCurrentThresholdViolationCleared NOTIFICATION-TYPE
   OBJECTS { sBTAModuleIndex, sBTAOutletIndex }
   STATUS current
   DESCRIPTION
      "INFORMATIONAL: A current threshold violation has been cleared.  Arguments specify
      the remote power device index and outlet number."
   --#TYPE "baytech: Current Alarm."
   --#SUMMARY "A current threshold violation has been cleared."
   --#SEVERITY INFORMATIONAL
   --#TIMEINDEX 1
   --#HELP ""
   --#HELPTAG 0
   --#STATE OPERATIONAL
   ::= { v2Notifications 47}

circuitPowerFactorThresholdWarning NOTIFICATION-TYPE
   OBJECTS { sBTAModuleIndex, sBTACircuitIndex }
   STATUS current
   DESCRIPTION
       "WARNING: The specified circuit has dropped below required Power Factor."
   --#TYPE "baytech: circuit power factor threshold violation."
   --#SUMMARY "power/VA Power Factor below threshold "
   --#SEVERITY WARNING
   --#TIMEINDEX 1
   --#HELP ""
   --#HELPTAG 0
   --#STATE OPERATIONAL
   ::= { v2Notifications 48}
 
circuitPowerFactorThresholdWarningCleared NOTIFICATION-TYPE
   OBJECTS { sBTAModuleIndex, sBTACircuitIndex }
   STATUS current
   DESCRIPTION
       "The specified circuit has returned to required Power Factor."
   --#TYPE "baytech: circuit power factor threshold violation cleared."
   --#SUMMARY "power/VA Power Factor at or above threshold "
   --#SEVERITY WARNING
   --#TIMEINDEX 1
   --#HELP ""
   --#HELPTAG 0
   --#STATE OPERATIONAL
   ::= { v2Notifications 49}

outletPowerFactorThresholdWarning NOTIFICATION-TYPE
   OBJECTS { sBTAModuleIndex, sBTAOutletIndex }
   STATUS current
   DESCRIPTION
       "WARNING: The specified circuit has dropped below required Power Factor."
   --#TYPE "baytech: outlet power factor threshold violation."
   --#SUMMARY "outlet power/VA Power Factor below threshold "
   --#SEVERITY WARNING
   --#TIMEINDEX 1
   --#HELP ""
   --#HELPTAG 0
   --#STATE OPERATIONAL
   ::= { v2Notifications 50}
 
 outletPowerFactorThresholdWarningCleared NOTIFICATION-TYPE
   OBJECTS { sBTAModuleIndex, sBTAOutletIndex }
   STATUS current
   DESCRIPTION
       "The specified circuit has returned to required Power Factor."
   --#TYPE "baytech: outlet power factor threshold violation cleared."
   --#SUMMARY "outlet power/VA Power Factor at or above threshold "
   --#SEVERITY WARNING
   --#TIMEINDEX 1
   --#HELP ""
   --#HELPTAG 0
   --#STATE OPERATIONAL
   ::= { v2Notifications 51}
   
inputCurrentThresholdViolation NOTIFICATION-TYPE
   OBJECTS { sBTAModuleIndex, sBTAInputIndex }
   STATUS current
   DESCRIPTION
      "INFORMATIONAL: A current threshold violation has been cleared.  Arguments specify
      the remote power device index and input number."
   --#TYPE "baytech: Input Current Alarm."
   --#SUMMARY "A current threshold has been violated."
   --#SEVERITY WARNING
   --#TIMEINDEX 1
   --#HELP ""
   --#HELPTAG 0
   --#STATE OPERATIONAL
   ::= { v2Notifications 52}

inputCurrentThresholdViolationCleared NOTIFICATION-TYPE
   OBJECTS { sBTAModuleIndex, sBTAInputIndex }
   STATUS current
   DESCRIPTION
      "INFORMATIONAL: A current threshold violation has been cleared.  Arguments specify
      the remote power device index and input number."
   --#TYPE "baytech: Input Current Alarm."
   --#SUMMARY "A current threshold violation has been cleared."
   --#SEVERITY INFORMATIONAL
   --#TIMEINDEX 1
   --#HELP ""
   --#HELPTAG 0
   --#STATE OPERATIONAL
   ::= { v2Notifications 53}

inputPowerFactorThresholdWarning NOTIFICATION-TYPE
   OBJECTS { sBTAModuleIndex, sBTAInputIndex }
   STATUS current
   DESCRIPTION
       "WARNING: The specified circuit has dropped below required Power Factor."
   --#TYPE "baytech: input power factor threshold violation."
   --#SUMMARY "input power/VA Power Factor below threshold "
   --#SEVERITY WARNING
   --#TIMEINDEX 1
   --#HELP ""
   --#HELPTAG 0
   --#STATE OPERATIONAL
   ::= { v2Notifications 54}
 
inputPowerFactorThresholdWarningCleared NOTIFICATION-TYPE
   OBJECTS { sBTAModuleIndex, sBTAInputIndex }
   STATUS current
   DESCRIPTION
       "The specified circuit has returned to required Power Factor."
   --#TYPE "baytech: input power factor threshold violation cleared."
   --#SUMMARY "input power/VA Power Factor at or above threshold "
   --#SEVERITY WARNING
   --#TIMEINDEX 1
   --#HELP ""
   --#HELPTAG 0
   --#STATE OPERATIONAL
   ::= { v2Notifications 55}

sourceVoltageOverThresholdViolation NOTIFICATION-TYPE
   OBJECTS { sBTAModuleIndex, sBTAVoltageSource }
   STATUS current
   DESCRIPTION
      "WARNING: Over voltage. Argument specifies voltage source number."
   --#TYPE "baytech: over voltage."
   --#SUMMARY "Over voltage."
   --#SEVERITY WARNING
   --#TIMEINDEX 1
   --#HELP ""
   --#HELPTAG 0
   --#STATE OPERATIONAL
   ::= { v2Notifications 56}

sourceVoltageOverThresholdViolationCleared NOTIFICATION-TYPE
   OBJECTS { sBTAModuleIndex, sBTAVoltageSource }
   STATUS current
   DESCRIPTION
      "INFORMATIONAL: Over voltage cleared. Argument specifies voltage source number."
   --#TYPE "baytech: over voltage cleared."
   --#SUMMARY "Over voltage cleared."
   --#SEVERITY INFORMATIONAL
   --#TIMEINDEX 1
   --#HELP ""
   --#HELPTAG 0
   --#STATE OPERATIONAL
   ::= { v2Notifications 57}

sourceVoltageUnderThresholdViolation NOTIFICATION-TYPE
   OBJECTS { sBTAModuleIndex, sBTAVoltageSource }
   STATUS current
   DESCRIPTION
      "WARNING: Under voltage. Argument specifies voltage source number."
   --#TYPE "baytech: under voltage."
   --#SUMMARY "Under voltage."
   --#SEVERITY WARNING
   --#TIMEINDEX 1
   --#HELP ""
   --#HELPTAG 0
   --#STATE OPERATIONAL
   ::= { v2Notifications 58}

sourceVoltageUnderThresholdViolationCleared NOTIFICATION-TYPE
   OBJECTS {sBTAModuleIndex, sBTAVoltageSource }
   STATUS current
   DESCRIPTION
      "INFORMATIONAL: Under voltage cleared. Argument specifies voltage source number."
   --#TYPE "baytech: under voltage cleared."
   --#SUMMARY "Under voltage cleared."
   --#SEVERITY INFORMATIONAL
   --#TIMEINDEX 1
   --#HELP ""
   --#HELPTAG 0
   --#STATE OPERATIONAL
   ::= { v2Notifications 59}

END
