EATON-EPDU-PU-SW-MIB DEFINITIONS ::= BEGIN

IMPORTS
    NOTIFICATION-TYPE, OBJECT-TYPE, MODULE-IDENTITY, 
    enterprises, IpAddress, Integer32
        FROM SNMPv2-SMI
    NOTIFICATION-GROUP, OBJECT-GROUP, MODULE-COMPLIANCE
        FROM SNMPv2-CONF;

pulizzi MODULE-IDENTITY
    LAST-UPDATED "200910161200Z"
    ORGANIZATION 
        "Eaton Corporation"
    CONTACT-INFO 
        "Eaton Corporation
                    Technical Resource Center phone numbers 
                    United States:  1.800.843.9433 or 919.870.3028
                    Canada:  1.800.461.9166 ext. 260
                    All other countries:  Call your local service representative."
    DESCRIPTION 
        "The MIB module for Eaton Switched ePDUs (Enclosed Power Distribution Units.)"

    REVISION "200910161200Z"
    DESCRIPTION 
        "
         Updated to add objects for units with up to 36 outlets and up to six measurement sections:
           - Added outlet25 through outlet36 branches under outletConfig
           - Added variables for outlets 25 through 36 under outletControl and outletStatus
           - Added outletSection4Config, outletSection5Config, and outletSection6Config
           - Added outletSection4, outletSection5, and outletSection6
           - Added the events branch and defined the appropriate notifications
           - Added the eventInfo branch to define objects used in notifications
           - Deprecated totalVoltage as it is no longer useful
           - Updated the conformance groups
        "

    REVISION "200812221200Z"
    DESCRIPTION 
        "
         Updated to fix syntax errors:
           - Added conformance groups
           - Filled in descriptions for all variables
           - Renamed the following variables: outletSection1Log to outletSection1Alert,
             outletSection2Log to outletSection2Alert, outletSection3Log to outletSection3Alert,
             tempSensor1Log to tempSensor1Alert, tempSensor2Log to tempSensor2Alert,
             humSensor1Log to humSensor1Alert, contactClosure1Log to contactClosure1Alert,
             contactClosure2Log to contactClosure2Alert, contactClosure3Log to contactClosure3Alert,
          keyBoardTime to loginTimeout; changed 'allert' to 'alert' wherever it appeared
        - Renamed MIB file to EATON-EPDU-PU-SW-MIB
        "

    REVISION "200802131200Z"
    DESCRIPTION 
        "
                 - CHANGED DISPLAYSTRING DATA TYPE TO OCTET STRING
                 - CHANGED GLOBAL COMMAND, PING ENABLED, AND PING INTERVAL
                 - CHANGED IP ADDRESS, SUBNET MASK, DEFAULT GATEWAY TO READ-ONLY
              "

    REVISION "200605011200Z"
    DESCRIPTION 
        "
                 INITIAL RELEASE.
              "
::= { enterprises 20677 }

ipv3600              OBJECT IDENTIFIER ::= { pulizzi 2 }
unitConfig           OBJECT IDENTIFIER ::= { ipv3600 1 }
networkSettings      OBJECT IDENTIFIER ::= { ipv3600 2 }
logManagerConfig     OBJECT IDENTIFIER ::= { ipv3600 3 }
serialSettings       OBJECT IDENTIFIER ::= { ipv3600 4 }
telnetSettings       OBJECT IDENTIFIER ::= { ipv3600 5 }
outletMngt           OBJECT IDENTIFIER ::= { ipv3600 6 }
outletConfig         OBJECT IDENTIFIER ::= { outletMngt 1 }
outlet1              OBJECT IDENTIFIER ::= { outletConfig 1 }
outlet2              OBJECT IDENTIFIER ::= { outletConfig 2 }
outlet3              OBJECT IDENTIFIER ::= { outletConfig 3 }
outlet4              OBJECT IDENTIFIER ::= { outletConfig 4 }
outlet5              OBJECT IDENTIFIER ::= { outletConfig 5 }
outlet6              OBJECT IDENTIFIER ::= { outletConfig 6 }
outlet7              OBJECT IDENTIFIER ::= { outletConfig 7 }
outlet8              OBJECT IDENTIFIER ::= { outletConfig 8 }
outlet9              OBJECT IDENTIFIER ::= { outletConfig 9 }
outlet10             OBJECT IDENTIFIER ::= { outletConfig 10 }
outlet11             OBJECT IDENTIFIER ::= { outletConfig 11 }
outlet12             OBJECT IDENTIFIER ::= { outletConfig 12 }
outlet13             OBJECT IDENTIFIER ::= { outletConfig 13 }
outlet14             OBJECT IDENTIFIER ::= { outletConfig 14 }
outlet15             OBJECT IDENTIFIER ::= { outletConfig 15 }
outlet16             OBJECT IDENTIFIER ::= { outletConfig 16 }
outlet17             OBJECT IDENTIFIER ::= { outletConfig 17 }
outlet18             OBJECT IDENTIFIER ::= { outletConfig 18 }
outlet19             OBJECT IDENTIFIER ::= { outletConfig 19 }
outlet20             OBJECT IDENTIFIER ::= { outletConfig 20 }
outlet21             OBJECT IDENTIFIER ::= { outletConfig 21 }
outlet22             OBJECT IDENTIFIER ::= { outletConfig 22 }
outlet23             OBJECT IDENTIFIER ::= { outletConfig 23 }
outlet24             OBJECT IDENTIFIER ::= { outletConfig 24 }
outlet25             OBJECT IDENTIFIER ::= { outletConfig 25 }
outlet26             OBJECT IDENTIFIER ::= { outletConfig 26 }
outlet27             OBJECT IDENTIFIER ::= { outletConfig 27 }
outlet28             OBJECT IDENTIFIER ::= { outletConfig 28 }
outlet29             OBJECT IDENTIFIER ::= { outletConfig 29 }
outlet30             OBJECT IDENTIFIER ::= { outletConfig 30 }
outlet31             OBJECT IDENTIFIER ::= { outletConfig 31 }
outlet32             OBJECT IDENTIFIER ::= { outletConfig 32 }
outlet33             OBJECT IDENTIFIER ::= { outletConfig 33 }
outlet34             OBJECT IDENTIFIER ::= { outletConfig 34 }
outlet35             OBJECT IDENTIFIER ::= { outletConfig 35 }
outlet36             OBJECT IDENTIFIER ::= { outletConfig 36 }
outletControl        OBJECT IDENTIFIER ::= { outletMngt 2 }
outletStatus         OBJECT IDENTIFIER ::= { outletMngt 3 }
snmpSettings         OBJECT IDENTIFIER ::= { ipv3600 7 }
snmpTraps            OBJECT IDENTIFIER ::= { snmpSettings 8 }
environmentalSettings  OBJECT IDENTIFIER ::= { ipv3600 8 }
temperatureSensorConfig  OBJECT IDENTIFIER ::= { environmentalSettings 1 }
tempSensor1          OBJECT IDENTIFIER ::= { temperatureSensorConfig 1 }
tempSensor2          OBJECT IDENTIFIER ::= { temperatureSensorConfig 2 }
humiditySensorConfig  OBJECT IDENTIFIER ::= { environmentalSettings 2 }
humSensor1           OBJECT IDENTIFIER ::= { humiditySensorConfig 1 }
contactClosureConfig  OBJECT IDENTIFIER ::= { environmentalSettings 3 }
contactClosure1      OBJECT IDENTIFIER ::= { contactClosureConfig 1 }
contactClosure2      OBJECT IDENTIFIER ::= { contactClosureConfig 2 }
contactClosure3      OBJECT IDENTIFIER ::= { contactClosureConfig 3 }
outletSectionConfig  OBJECT IDENTIFIER ::= { environmentalSettings 4 }
outletSection1Config  OBJECT IDENTIFIER ::= { outletSectionConfig 1 }
outletSection2Config  OBJECT IDENTIFIER ::= { outletSectionConfig 2 }
outletSection3Config  OBJECT IDENTIFIER ::= { outletSectionConfig 3 }
outletSection4Config  OBJECT IDENTIFIER ::= { outletSectionConfig 4 }
outletSection5Config  OBJECT IDENTIFIER ::= { outletSectionConfig 5 }
outletSection6Config  OBJECT IDENTIFIER ::= { outletSectionConfig 6 }
currentSensorValues  OBJECT IDENTIFIER ::= { environmentalSettings 5 }
currentOutletSectionValues  OBJECT IDENTIFIER ::= { environmentalSettings 6 }
outletSection1       OBJECT IDENTIFIER ::= { currentOutletSectionValues 1 }
outletSection2       OBJECT IDENTIFIER ::= { currentOutletSectionValues 2 }
outletSection3       OBJECT IDENTIFIER ::= { currentOutletSectionValues 3 }
total                OBJECT IDENTIFIER ::= { currentOutletSectionValues 4 }
outletSection4       OBJECT IDENTIFIER ::= { currentOutletSectionValues 5 }
outletSection5       OBJECT IDENTIFIER ::= { currentOutletSectionValues 6 }
outletSection6       OBJECT IDENTIFIER ::= { currentOutletSectionValues 7 }
events               OBJECT IDENTIFIER ::= { ipv3600 9 }
eventInfo            OBJECT IDENTIFIER ::= { ipv3600 10 }
conformance          OBJECT IDENTIFIER ::= { ipv3600 25 }
groups               OBJECT IDENTIFIER ::= { conformance 5 }

unitName  OBJECT-TYPE
    SYNTAX     OCTET STRING (SIZE(1..20))
    MAX-ACCESS read-write
    STATUS     current
    DESCRIPTION 
        "Descriptive name of unit."
    ::= { unitConfig 1 }

strappingId  OBJECT-TYPE
    SYNTAX     Integer32 (0..23)
    MAX-ACCESS read-only
    STATUS     current
    DESCRIPTION 
        "ID of unit when connected in a strapping configuration."
    ::= { unitConfig 2 }

unitTime  OBJECT-TYPE
    SYNTAX     OCTET STRING (SIZE(1..5))
    MAX-ACCESS read-write
    STATUS     current
    DESCRIPTION 
        "Time hh:mm"
    ::= { unitConfig 3 }

unitDate  OBJECT-TYPE
    SYNTAX     OCTET STRING (SIZE(1..10))
    MAX-ACCESS read-write
    STATUS     current
    DESCRIPTION 
        "Today's date mm/dd/yyyy"
    ::= { unitConfig 4 }

unitDayOfWeek  OBJECT-TYPE
    SYNTAX     INTEGER {
        sunday (1),
        monday (2),
        tuesday (3),
        wednesday (4),
        thursday (5),
        friday (6),
        saturday (7)
    }
    MAX-ACCESS read-write
    STATUS     current
    DESCRIPTION 
        "Today's day of week.  This is important when scheduling logs to be sent on a particular week day."
    ::= { unitConfig 5 }

vaLoggingInterval  OBJECT-TYPE
    SYNTAX     INTEGER {
        disabled (0),
        fiveminutes (1),
        fifteenminutes (2),
        hourly (3)
    }
    MAX-ACCESS read-write
    STATUS     current
    DESCRIPTION 
        "Interval for updating the VA log."
    ::= { unitConfig 6 }

loginTimeout  OBJECT-TYPE
    SYNTAX     Integer32
    MAX-ACCESS read-write
    STATUS     current
    DESCRIPTION 
        "Timeout (in seconds) for serial, telnet, and web interfaces."
    ::= { unitConfig 7 }

invertDisplay  OBJECT-TYPE
    SYNTAX     INTEGER {
        normal (0),
        inverted (1)
    }
    MAX-ACCESS read-write
    STATUS     current
    DESCRIPTION 
        "Select the orientation of the local 7-segment display."
    ::= { unitConfig 8 }

fahrenheitOrCelsius  OBJECT-TYPE
    SYNTAX     INTEGER {
        fahrenheit (0),
        celsius (1)
    }
    MAX-ACCESS read-write
    STATUS     current
    DESCRIPTION 
        "Units for temperature readings."
    ::= { unitConfig 9 }

unitIPAddress  OBJECT-TYPE
    SYNTAX     IpAddress
    MAX-ACCESS read-only
    STATUS     current
    DESCRIPTION 
        "Network IP address"
    ::= { networkSettings 1 }

subnetMask  OBJECT-TYPE
    SYNTAX     IpAddress
    MAX-ACCESS read-only
    STATUS     current
    DESCRIPTION 
        "Network subnet mask"
    ::= { networkSettings 2 }

defaultGateway  OBJECT-TYPE
    SYNTAX     IpAddress
    MAX-ACCESS read-only
    STATUS     current
    DESCRIPTION 
        "Network default gateway"
    ::= { networkSettings 3 }

webPort  OBJECT-TYPE
    SYNTAX     Integer32
    MAX-ACCESS read-write
    STATUS     current
    DESCRIPTION 
        "Port number for non-secure (http) web interface."
    ::= { networkSettings 4 }

webEnabled  OBJECT-TYPE
    SYNTAX     INTEGER {
        enabled (1),
        disabled (2)
    }
    MAX-ACCESS read-write
    STATUS     current
    DESCRIPTION 
        "Enables or disables the web interface (both secure and non-secure)."
    ::= { networkSettings 5 }

macAddress  OBJECT-TYPE
    SYNTAX     OCTET STRING (SIZE(1..17))
    MAX-ACCESS read-only
    STATUS     current
    DESCRIPTION 
        "Hardware network address"
    ::= { networkSettings 6 }

enablePing  OBJECT-TYPE
    SYNTAX     INTEGER {
        disabled (0),
        enabled (1)
    }
    MAX-ACCESS read-write
    STATUS     current
    DESCRIPTION 
        "Enables ping watchdog feature.  If enabled, the IP address for each outlet (if non-zero) will be pinged
         periodically; the outlet will be rebooted if there is no ping response."
    ::= { networkSettings 7 }

pingInterval  OBJECT-TYPE
    SYNTAX     Integer32 (1..999)
    MAX-ACCESS read-write
    STATUS     current
    DESCRIPTION 
        "Interval (in minutes) beween attempts to ping the IP address corresponding to an outlet."
    ::= { networkSettings 8 }

mailServerIPAddress  OBJECT-TYPE
    SYNTAX     IpAddress
    MAX-ACCESS read-write
    STATUS     current
    DESCRIPTION 
        "IP address of mail server for sending logs and alerts."
    ::= { logManagerConfig 1 }

sendLogFrom  OBJECT-TYPE
    SYNTAX     OCTET STRING
    MAX-ACCESS read-write
    STATUS     current
    DESCRIPTION 
        "Email address (x@y.z format) to be used as the from address for logs and alerts."
    ::= { logManagerConfig 2 }

sendLogToUser1Address  OBJECT-TYPE
    SYNTAX     OCTET STRING
    MAX-ACCESS read-write
    STATUS     current
    DESCRIPTION 
        "Email address to which to send unit logs."
    ::= { logManagerConfig 3 }

sendLogToUser2Address  OBJECT-TYPE
    SYNTAX     OCTET STRING
    MAX-ACCESS read-write
    STATUS     current
    DESCRIPTION 
        "Second email address to which to send unit logs."
    ::= { logManagerConfig 4 }

sendAlertsToUser1Address  OBJECT-TYPE
    SYNTAX     OCTET STRING
    MAX-ACCESS read-write
    STATUS     current
    DESCRIPTION 
        "Email address to which to send unit alerts."
    ::= { logManagerConfig 5 }

sendAlertsToUser2Address  OBJECT-TYPE
    SYNTAX     OCTET STRING
    MAX-ACCESS read-write
    STATUS     current
    DESCRIPTION 
        "Second email address to which to send unit alerts."
    ::= { logManagerConfig 6 }

sendLogFrequency  OBJECT-TYPE
    SYNTAX     INTEGER {
        weeklyOnSunday (1),
        weeklyOnMonday (2),
        weeklyOnTuesday (3),
        weeklyOnWednesday (4),
        weeklyOnThursday (5),
        weeklyOnFriday (6),
        weeklyOnSaturday (7),
        daily (8),
        whenFull (9),
        never (10)
    }
    MAX-ACCESS read-write
    STATUS     current
    DESCRIPTION 
        "Frequency with which to send logs via email."
    ::= { logManagerConfig 7 }

sendLogTime  OBJECT-TYPE
    SYNTAX     OCTET STRING
    MAX-ACCESS read-write
    STATUS     current
    DESCRIPTION 
        "Time of day to send logs via email.  Not applicable if sendLogFrequency is set to whenFull or never."
    ::= { logManagerConfig 8 }

userLogInLogOut  OBJECT-TYPE
    SYNTAX     INTEGER {
        disabled (1),
        sendToLog (2),
        sendAlert (3),
        sendtoLogAndAlert (4)
    }
    MAX-ACCESS read-write
    STATUS     current
    DESCRIPTION 
        "Enabled setting to log or send an alert when a user logs in or logs out of the serial, telnet, or web interfaces."
    ::= { logManagerConfig 9 }

userLogInLogOutFailed  OBJECT-TYPE
    SYNTAX     INTEGER {
        disabled (1),
        sendToLog (2),
        sendAlert (3),
        sendtoLogAndAlert (4)
    }
    MAX-ACCESS read-write
    STATUS     current
    DESCRIPTION 
        "Enabled setting to log or send an alert when a user attempts to log in but fails because of a username or password mismatch."
    ::= { logManagerConfig 10 }

outletActivity  OBJECT-TYPE
    SYNTAX     INTEGER {
        disabled (1),
        sendToLog (2),
        sendAlert (3),
        sendtoLogAndAlert (4)
    }
    MAX-ACCESS read-write
    STATUS     current
    DESCRIPTION 
        "Enabled setting to log or send an alert each time an outlet changes state."
    ::= { logManagerConfig 11 }

systemOnOff  OBJECT-TYPE
    SYNTAX     INTEGER {
        disabled (1),
        sendToLog (2),
        sendAlert (3),
        sendtoLogAndAlert (4)
    }
    MAX-ACCESS read-write
    STATUS     current
    DESCRIPTION 
        "Enabled setting to log or send an alert each time the unit powers up."
    ::= { logManagerConfig 12 }

outletSection1Alert  OBJECT-TYPE
    SYNTAX     INTEGER {
        disabled (0),
        sendAlert (1)
    }
    MAX-ACCESS read-write
    STATUS     current
    DESCRIPTION 
        "Enabled setting to send an email alert when section 1 thresholds are breached."
    ::= { logManagerConfig 13 }

outletSection2Alert  OBJECT-TYPE
    SYNTAX     INTEGER {
        disabled (0),
        sendAlert (1)
    }
    MAX-ACCESS read-write
    STATUS     current
    DESCRIPTION 
        "Enabled setting to send an email alert when section 2 thresholds are brached."
    ::= { logManagerConfig 14 }

outletSection3Alert  OBJECT-TYPE
    SYNTAX     INTEGER {
        disabled (0),
        sendAlert (1)
    }
    MAX-ACCESS read-write
    STATUS     current
    DESCRIPTION 
        "Enabled setting to send an email alert when section 3 thresholds are breached."
    ::= { logManagerConfig 15 }

tempSensor1Alert  OBJECT-TYPE
    SYNTAX     INTEGER {
        disabled (0),
        sendAlert (1)
    }
    MAX-ACCESS read-write
    STATUS     current
    DESCRIPTION 
        "Enabled setting to send an email alert when temperature sensor 1 thresholds are breached."
    ::= { logManagerConfig 16 }

tempSensor2Alert  OBJECT-TYPE
    SYNTAX     INTEGER {
        disabled (0),
        sendAlert (1)
    }
    MAX-ACCESS read-write
    STATUS     current
    DESCRIPTION 
        "Enabled setting to send an email alert when temperature sensor 2 thresholds are breached."
    ::= { logManagerConfig 17 }

humSensor1Alert  OBJECT-TYPE
    SYNTAX     INTEGER {
        disabled (0),
        sendAlert (1)
    }
    MAX-ACCESS read-write
    STATUS     current
    DESCRIPTION 
        "Enabled setting to send an email alert when humidity sensor thresholds are breached."
    ::= { logManagerConfig 18 }

contactClosure1Alert  OBJECT-TYPE
    SYNTAX     INTEGER {
        disabled (0),
        sendAlert (1)
    }
    MAX-ACCESS read-write
    STATUS     current
    DESCRIPTION 
        "Enabled setting to send an email alert when contact sensor 1 changes state."
    ::= { logManagerConfig 19 }

contactClosure2Alert  OBJECT-TYPE
    SYNTAX     INTEGER {
        disabled (0),
        sendAlert (1)
    }
    MAX-ACCESS read-write
    STATUS     current
    DESCRIPTION 
        "Enabled setting to send an email alert when contact sensor 2 changes state."
    ::= { logManagerConfig 20 }

contactClosure3Alert  OBJECT-TYPE
    SYNTAX     INTEGER {
        disabled (0),
        sendAlert (1)
    }
    MAX-ACCESS read-write
    STATUS     current
    DESCRIPTION 
        "Enabled setting to send an email alert when contact sensor 3 changes state."
    ::= { logManagerConfig 21 }

baudRate  OBJECT-TYPE
    SYNTAX     INTEGER {
        baud9600 (0),
        baud19200 (1),
        baud38400 (2)
    }
    MAX-ACCESS read-write
    STATUS     current
    DESCRIPTION 
        "Serial baud rate, does not take effect unless unit is soft-rebooted."
    ::= { serialSettings 1 }

telnetPort  OBJECT-TYPE
    SYNTAX     Integer32
    MAX-ACCESS read-write
    STATUS     current
    DESCRIPTION 
        "Telnet interface port, default is 23."
    ::= { telnetSettings 1 }

telnetEnabled  OBJECT-TYPE
    SYNTAX     INTEGER {
        enabled (1),
        disabled (2)
    }
    MAX-ACCESS read-write
    STATUS     current
    DESCRIPTION 
        "Enabled setting for the telnet interface.  This can be disabled for security."
    ::= { telnetSettings 2 }

outlet1Name  OBJECT-TYPE
    SYNTAX     OCTET STRING (SIZE(1..20))
    MAX-ACCESS read-write
    STATUS     current
    DESCRIPTION 
        "Descriptive outlet name"
    ::= { outlet1 1 }

outlet1PingIpAddress  OBJECT-TYPE
    SYNTAX     IpAddress
    MAX-ACCESS read-write
    STATUS     current
    DESCRIPTION 
        "Ping watchdog IP address"
    ::= { outlet1 2 }

outlet1Link  OBJECT-TYPE
    SYNTAX     OCTET STRING
    MAX-ACCESS read-write
    STATUS     current
    DESCRIPTION 
        "URL of web configuration interface for the device connected to this outlet."
    ::= { outlet1 3 }

outlet1SequenceTime  OBJECT-TYPE
    SYNTAX     Integer32
    MAX-ACCESS read-write
    STATUS     current
    DESCRIPTION 
        "Time in seconds for the outlet to delay turning on after a Sequence On command is issued."
    ::= { outlet1 4 }

outlet1RebootTime  OBJECT-TYPE
    SYNTAX     Integer32
    MAX-ACCESS read-write
    STATUS     current
    DESCRIPTION 
        "Time in seconds for the outlet to remain off when a Reboot command is issued."
    ::= { outlet1 5 }

outlet2Name  OBJECT-TYPE
    SYNTAX     OCTET STRING (SIZE(1..20))
    MAX-ACCESS read-write
    STATUS     current
    DESCRIPTION 
        "Descriptive outlet name"
    ::= { outlet2 1 }

outlet2PingIpAddress  OBJECT-TYPE
    SYNTAX     IpAddress
    MAX-ACCESS read-write
    STATUS     current
    DESCRIPTION 
        "Ping watchdog IP address"
    ::= { outlet2 2 }

outlet2Link  OBJECT-TYPE
    SYNTAX     OCTET STRING
    MAX-ACCESS read-write
    STATUS     current
    DESCRIPTION 
        "URL of web configuration interface for the device connected to this outlet."
    ::= { outlet2 3 }

outlet2SequenceTime  OBJECT-TYPE
    SYNTAX     Integer32
    MAX-ACCESS read-write
    STATUS     current
    DESCRIPTION 
        "Time in seconds for the outlet to delay turning on after a Sequence On command is issued."
    ::= { outlet2 4 }

outlet2RebootTime  OBJECT-TYPE
    SYNTAX     Integer32
    MAX-ACCESS read-write
    STATUS     current
    DESCRIPTION 
        "Time in seconds for the outlet to remain off when a Reboot command is issued."
    ::= { outlet2 5 }

outlet3Name  OBJECT-TYPE
    SYNTAX     OCTET STRING (SIZE(1..20))
    MAX-ACCESS read-write
    STATUS     current
    DESCRIPTION 
        "Descriptive outlet name"
    ::= { outlet3 1 }

outlet3PingIpAddress  OBJECT-TYPE
    SYNTAX     IpAddress
    MAX-ACCESS read-write
    STATUS     current
    DESCRIPTION 
        "Ping watchdog IP address"
    ::= { outlet3 2 }

outlet3Link  OBJECT-TYPE
    SYNTAX     OCTET STRING
    MAX-ACCESS read-write
    STATUS     current
    DESCRIPTION 
        "URL of web configuration interface for the device connected to this outlet."
    ::= { outlet3 3 }

outlet3SequenceTime  OBJECT-TYPE
    SYNTAX     Integer32
    MAX-ACCESS read-write
    STATUS     current
    DESCRIPTION 
        "Time in seconds for the outlet to delay turning on after a Sequence On command is issued."
    ::= { outlet3 4 }

outlet3RebootTime  OBJECT-TYPE
    SYNTAX     Integer32
    MAX-ACCESS read-write
    STATUS     current
    DESCRIPTION 
        "Time in seconds for the outlet to remain off when a Reboot command is issued."
    ::= { outlet3 5 }

outlet4Name  OBJECT-TYPE
    SYNTAX     OCTET STRING (SIZE(1..20))
    MAX-ACCESS read-write
    STATUS     current
    DESCRIPTION 
        "Descriptive outlet name"
    ::= { outlet4 1 }

outlet4PingIpAddress  OBJECT-TYPE
    SYNTAX     IpAddress
    MAX-ACCESS read-write
    STATUS     current
    DESCRIPTION 
        "Ping watchdog IP address"
    ::= { outlet4 2 }

outlet4Link  OBJECT-TYPE
    SYNTAX     OCTET STRING
    MAX-ACCESS read-write
    STATUS     current
    DESCRIPTION 
        "URL of web configuration interface for the device connected to this outlet."
    ::= { outlet4 3 }

outlet4SequenceTime  OBJECT-TYPE
    SYNTAX     Integer32
    MAX-ACCESS read-write
    STATUS     current
    DESCRIPTION 
        "Time in seconds for the outlet to delay turning on after a Sequence On command is issued."
    ::= { outlet4 4 }

outlet4RebootTime  OBJECT-TYPE
    SYNTAX     Integer32
    MAX-ACCESS read-write
    STATUS     current
    DESCRIPTION 
        "Time in seconds for the outlet to remain off when a Reboot command is issued."
    ::= { outlet4 5 }

outlet5Name  OBJECT-TYPE
    SYNTAX     OCTET STRING (SIZE(1..20))
    MAX-ACCESS read-write
    STATUS     current
    DESCRIPTION 
        "Descriptive outlet name"
    ::= { outlet5 1 }

outlet5PingIpAddress  OBJECT-TYPE
    SYNTAX     IpAddress
    MAX-ACCESS read-write
    STATUS     current
    DESCRIPTION 
        "Ping watchdog IP address"
    ::= { outlet5 2 }

outlet5Link  OBJECT-TYPE
    SYNTAX     OCTET STRING
    MAX-ACCESS read-write
    STATUS     current
    DESCRIPTION 
        "URL of web configuration interface for the device connected to this outlet."
    ::= { outlet5 3 }

outlet5SequenceTime  OBJECT-TYPE
    SYNTAX     Integer32
    MAX-ACCESS read-write
    STATUS     current
    DESCRIPTION 
        "Time in seconds for the outlet to delay turning on after a Sequence On command is issued."
    ::= { outlet5 4 }

outlet5RebootTime  OBJECT-TYPE
    SYNTAX     Integer32
    MAX-ACCESS read-write
    STATUS     current
    DESCRIPTION 
        "Time in seconds for the outlet to remain off when a Reboot command is issued."
    ::= { outlet5 5 }

outlet6Name  OBJECT-TYPE
    SYNTAX     OCTET STRING (SIZE(1..20))
    MAX-ACCESS read-write
    STATUS     current
    DESCRIPTION 
        "Descriptive outlet name"
    ::= { outlet6 1 }

outlet6PingIpAddress  OBJECT-TYPE
    SYNTAX     IpAddress
    MAX-ACCESS read-write
    STATUS     current
    DESCRIPTION 
        "Ping watchdog IP address"
    ::= { outlet6 2 }

outlet6Link  OBJECT-TYPE
    SYNTAX     OCTET STRING
    MAX-ACCESS read-write
    STATUS     current
    DESCRIPTION 
        "URL of web configuration interface for the device connected to this outlet."
    ::= { outlet6 3 }

outlet6SequenceTime  OBJECT-TYPE
    SYNTAX     Integer32
    MAX-ACCESS read-write
    STATUS     current
    DESCRIPTION 
        "Time in seconds for the outlet to delay turning on after a Sequence On command is issued."
    ::= { outlet6 4 }

outlet6RebootTime  OBJECT-TYPE
    SYNTAX     Integer32
    MAX-ACCESS read-write
    STATUS     current
    DESCRIPTION 
        "Time in seconds for the outlet to remain off when a Reboot command is issued."
    ::= { outlet6 5 }

outlet7Name  OBJECT-TYPE
    SYNTAX     OCTET STRING (SIZE(1..20))
    MAX-ACCESS read-write
    STATUS     current
    DESCRIPTION 
        "Descriptive outlet name"
    ::= { outlet7 1 }

outlet7PingIpAddress  OBJECT-TYPE
    SYNTAX     IpAddress
    MAX-ACCESS read-write
    STATUS     current
    DESCRIPTION 
        "Ping watchdog IP address"
    ::= { outlet7 2 }

outlet7Link  OBJECT-TYPE
    SYNTAX     OCTET STRING
    MAX-ACCESS read-write
    STATUS     current
    DESCRIPTION 
        "URL of web configuration interface for the device connected to this outlet."
    ::= { outlet7 3 }

outlet7SequenceTime  OBJECT-TYPE
    SYNTAX     Integer32
    MAX-ACCESS read-write
    STATUS     current
    DESCRIPTION 
        "Time in seconds for the outlet to delay turning on after a Sequence On command is issued."
    ::= { outlet7 4 }

outlet7RebootTime  OBJECT-TYPE
    SYNTAX     Integer32
    MAX-ACCESS read-write
    STATUS     current
    DESCRIPTION 
        "Time in seconds for the outlet to remain off when a Reboot command is issued."
    ::= { outlet7 5 }

outlet8Name  OBJECT-TYPE
    SYNTAX     OCTET STRING (SIZE(1..20))
    MAX-ACCESS read-write
    STATUS     current
    DESCRIPTION 
        "Descriptive outlet name"
    ::= { outlet8 1 }

outlet8PingIpAddress  OBJECT-TYPE
    SYNTAX     IpAddress
    MAX-ACCESS read-write
    STATUS     current
    DESCRIPTION 
        "Ping watchdog IP address"
    ::= { outlet8 2 }

outlet8Link  OBJECT-TYPE
    SYNTAX     OCTET STRING
    MAX-ACCESS read-write
    STATUS     current
    DESCRIPTION 
        "URL of web configuration interface for the device connected to this outlet."
    ::= { outlet8 3 }

outlet8SequenceTime  OBJECT-TYPE
    SYNTAX     Integer32
    MAX-ACCESS read-write
    STATUS     current
    DESCRIPTION 
        "Time in seconds for the outlet to delay turning on after a Sequence On command is issued."
    ::= { outlet8 4 }

outlet8RebootTime  OBJECT-TYPE
    SYNTAX     Integer32
    MAX-ACCESS read-write
    STATUS     current
    DESCRIPTION 
        "Time in seconds for the outlet to remain off when a Reboot command is issued."
    ::= { outlet8 5 }

outlet9Name  OBJECT-TYPE
    SYNTAX     OCTET STRING (SIZE(1..20))
    MAX-ACCESS read-write
    STATUS     current
    DESCRIPTION 
        "Descriptive outlet name"
    ::= { outlet9 1 }

outlet9PingIpAddress  OBJECT-TYPE
    SYNTAX     IpAddress
    MAX-ACCESS read-write
    STATUS     current
    DESCRIPTION 
        "Ping watchdog IP address"
    ::= { outlet9 2 }

outlet9Link  OBJECT-TYPE
    SYNTAX     OCTET STRING
    MAX-ACCESS read-write
    STATUS     current
    DESCRIPTION 
        "URL of web configuration interface for the device connected to this outlet."
    ::= { outlet9 3 }

outlet9SequenceTime  OBJECT-TYPE
    SYNTAX     Integer32
    MAX-ACCESS read-write
    STATUS     current
    DESCRIPTION 
        "Time in seconds for the outlet to delay turning on after a Sequence On command is issued."
    ::= { outlet9 4 }

outlet9RebootTime  OBJECT-TYPE
    SYNTAX     Integer32
    MAX-ACCESS read-write
    STATUS     current
    DESCRIPTION 
        "Time in seconds for the outlet to remain off when a Reboot command is issued."
    ::= { outlet9 5 }

outlet10Name  OBJECT-TYPE
    SYNTAX     OCTET STRING (SIZE(1..20))
    MAX-ACCESS read-write
    STATUS     current
    DESCRIPTION 
        "Descriptive outlet name"
    ::= { outlet10 1 }

outlet10PingIpAddress  OBJECT-TYPE
    SYNTAX     IpAddress
    MAX-ACCESS read-write
    STATUS     current
    DESCRIPTION 
        "Ping watchdog IP address"
    ::= { outlet10 2 }

outlet10Link  OBJECT-TYPE
    SYNTAX     OCTET STRING
    MAX-ACCESS read-write
    STATUS     current
    DESCRIPTION 
        "URL of web configuration interface for the device connected to this outlet."
    ::= { outlet10 3 }

outlet10SequenceTime  OBJECT-TYPE
    SYNTAX     Integer32
    MAX-ACCESS read-write
    STATUS     current
    DESCRIPTION 
        "Time in seconds for the outlet to delay turning on after a Sequence On command is issued."
    ::= { outlet10 4 }

outlet10RebootTime  OBJECT-TYPE
    SYNTAX     Integer32
    MAX-ACCESS read-write
    STATUS     current
    DESCRIPTION 
        "Time in seconds for the outlet to remain off when a Reboot command is issued."
    ::= { outlet10 5 }

outlet11Name  OBJECT-TYPE
    SYNTAX     OCTET STRING (SIZE(1..20))
    MAX-ACCESS read-write
    STATUS     current
    DESCRIPTION 
        "Descriptive outlet name"
    ::= { outlet11 1 }

outlet11PingIpAddress  OBJECT-TYPE
    SYNTAX     IpAddress
    MAX-ACCESS read-write
    STATUS     current
    DESCRIPTION 
        "Ping watchdog IP address"
    ::= { outlet11 2 }

outlet11Link  OBJECT-TYPE
    SYNTAX     OCTET STRING
    MAX-ACCESS read-write
    STATUS     current
    DESCRIPTION 
        "URL of web configuration interface for the device connected to this outlet."
    ::= { outlet11 3 }

outlet11SequenceTime  OBJECT-TYPE
    SYNTAX     Integer32
    MAX-ACCESS read-write
    STATUS     current
    DESCRIPTION 
        "Time in seconds for the outlet to delay turning on after a Sequence On command is issued."
    ::= { outlet11 4 }

outlet11RebootTime  OBJECT-TYPE
    SYNTAX     Integer32
    MAX-ACCESS read-write
    STATUS     current
    DESCRIPTION 
        "Time in seconds for the outlet to remain off when a Reboot command is issued."
    ::= { outlet11 5 }

outlet12Name  OBJECT-TYPE
    SYNTAX     OCTET STRING (SIZE(1..20))
    MAX-ACCESS read-write
    STATUS     current
    DESCRIPTION 
        "Descriptive outlet name"
    ::= { outlet12 1 }

outlet12PingIpAddress  OBJECT-TYPE
    SYNTAX     IpAddress
    MAX-ACCESS read-write
    STATUS     current
    DESCRIPTION 
        "Ping watchdog IP address"
    ::= { outlet12 2 }

outlet12Link  OBJECT-TYPE
    SYNTAX     OCTET STRING
    MAX-ACCESS read-write
    STATUS     current
    DESCRIPTION 
        "URL of web configuration interface for the device connected to this outlet."
    ::= { outlet12 3 }

outlet12SequenceTime  OBJECT-TYPE
    SYNTAX     Integer32
    MAX-ACCESS read-write
    STATUS     current
    DESCRIPTION 
        "Time in seconds for the outlet to delay turning on after a Sequence On command is issued."
    ::= { outlet12 4 }

outlet12RebootTime  OBJECT-TYPE
    SYNTAX     Integer32
    MAX-ACCESS read-write
    STATUS     current
    DESCRIPTION 
        "Time in seconds for the outlet to remain off when a Reboot command is issued."
    ::= { outlet12 5 }

outlet13Name  OBJECT-TYPE
    SYNTAX     OCTET STRING (SIZE(1..20))
    MAX-ACCESS read-write
    STATUS     current
    DESCRIPTION 
        "Descriptive outlet name"
    ::= { outlet13 1 }

outlet13PingIpAddress  OBJECT-TYPE
    SYNTAX     IpAddress
    MAX-ACCESS read-write
    STATUS     current
    DESCRIPTION 
        "Ping watchdog IP address"
    ::= { outlet13 2 }

outlet13Link  OBJECT-TYPE
    SYNTAX     OCTET STRING
    MAX-ACCESS read-write
    STATUS     current
    DESCRIPTION 
        "URL of web configuration interface for the device connected to this outlet."
    ::= { outlet13 3 }

outlet13SequenceTime  OBJECT-TYPE
    SYNTAX     Integer32
    MAX-ACCESS read-write
    STATUS     current
    DESCRIPTION 
        "Time in seconds for the outlet to delay turning on after a Sequence On command is issued."
    ::= { outlet13 4 }

outlet13RebootTime  OBJECT-TYPE
    SYNTAX     Integer32
    MAX-ACCESS read-write
    STATUS     current
    DESCRIPTION 
        "Time in seconds for the outlet to remain off when a Reboot command is issued."
    ::= { outlet13 5 }

outlet14Name  OBJECT-TYPE
    SYNTAX     OCTET STRING (SIZE(1..20))
    MAX-ACCESS read-write
    STATUS     current
    DESCRIPTION 
        "Descriptive outlet name"
    ::= { outlet14 1 }

outlet14PingIpAddress  OBJECT-TYPE
    SYNTAX     IpAddress
    MAX-ACCESS read-write
    STATUS     current
    DESCRIPTION 
        "Ping watchdog IP address"
    ::= { outlet14 2 }

outlet14Link  OBJECT-TYPE
    SYNTAX     OCTET STRING
    MAX-ACCESS read-write
    STATUS     current
    DESCRIPTION 
        "URL of web configuration interface for the device connected to this outlet."
    ::= { outlet14 3 }

outlet14SequenceTime  OBJECT-TYPE
    SYNTAX     Integer32
    MAX-ACCESS read-write
    STATUS     current
    DESCRIPTION 
        "Time in seconds for the outlet to delay turning on after a Sequence On command is issued."
    ::= { outlet14 4 }

outlet14RebootTime  OBJECT-TYPE
    SYNTAX     Integer32
    MAX-ACCESS read-write
    STATUS     current
    DESCRIPTION 
        "Time in seconds for the outlet to remain off when a Reboot command is issued."
    ::= { outlet14 5 }

outlet15Name  OBJECT-TYPE
    SYNTAX     OCTET STRING (SIZE(1..20))
    MAX-ACCESS read-write
    STATUS     current
    DESCRIPTION 
        "Descriptive outlet name"
    ::= { outlet15 1 }

outlet15PingIpAddress  OBJECT-TYPE
    SYNTAX     IpAddress
    MAX-ACCESS read-write
    STATUS     current
    DESCRIPTION 
        "Ping watchdog IP address"
    ::= { outlet15 2 }

outlet15Link  OBJECT-TYPE
    SYNTAX     OCTET STRING
    MAX-ACCESS read-write
    STATUS     current
    DESCRIPTION 
        "URL of web configuration interface for the device connected to this outlet."
    ::= { outlet15 3 }

outlet15SequenceTime  OBJECT-TYPE
    SYNTAX     Integer32
    MAX-ACCESS read-write
    STATUS     current
    DESCRIPTION 
        "Time in seconds for the outlet to delay turning on after a Sequence On command is issued."
    ::= { outlet15 4 }

outlet15RebootTime  OBJECT-TYPE
    SYNTAX     Integer32
    MAX-ACCESS read-write
    STATUS     current
    DESCRIPTION 
        "Time in seconds for the outlet to remain off when a Reboot command is issued."
    ::= { outlet15 5 }

outlet16Name  OBJECT-TYPE
    SYNTAX     OCTET STRING (SIZE(1..20))
    MAX-ACCESS read-write
    STATUS     current
    DESCRIPTION 
        "Descriptive outlet name"
    ::= { outlet16 1 }

outlet16PingIpAddress  OBJECT-TYPE
    SYNTAX     IpAddress
    MAX-ACCESS read-write
    STATUS     current
    DESCRIPTION 
        "Ping watchdog IP address"
    ::= { outlet16 2 }

outlet16Link  OBJECT-TYPE
    SYNTAX     OCTET STRING
    MAX-ACCESS read-write
    STATUS     current
    DESCRIPTION 
        "URL of web configuration interface for the device connected to this outlet."
    ::= { outlet16 3 }

outlet16SequenceTime  OBJECT-TYPE
    SYNTAX     Integer32
    MAX-ACCESS read-write
    STATUS     current
    DESCRIPTION 
        "Time in seconds for the outlet to delay turning on after a Sequence On command is issued."
    ::= { outlet16 4 }

outlet16RebootTime  OBJECT-TYPE
    SYNTAX     Integer32
    MAX-ACCESS read-write
    STATUS     current
    DESCRIPTION 
        "Time in seconds for the outlet to remain off when a Reboot command is issued."
    ::= { outlet16 5 }

outlet17Name  OBJECT-TYPE
    SYNTAX     OCTET STRING (SIZE(1..20))
    MAX-ACCESS read-write
    STATUS     current
    DESCRIPTION 
        "Descriptive outlet name"
    ::= { outlet17 1 }

outlet17PingIpAddress  OBJECT-TYPE
    SYNTAX     IpAddress
    MAX-ACCESS read-write
    STATUS     current
    DESCRIPTION 
        "Ping watchdog IP address"
    ::= { outlet17 2 }

outlet17Link  OBJECT-TYPE
    SYNTAX     OCTET STRING
    MAX-ACCESS read-write
    STATUS     current
    DESCRIPTION 
        "URL of web configuration interface for the device connected to this outlet."
    ::= { outlet17 3 }

outlet17SequenceTime  OBJECT-TYPE
    SYNTAX     Integer32
    MAX-ACCESS read-write
    STATUS     current
    DESCRIPTION 
        "Time in seconds for the outlet to delay turning on after a Sequence On command is issued."
    ::= { outlet17 4 }

outlet17RebootTime  OBJECT-TYPE
    SYNTAX     Integer32
    MAX-ACCESS read-write
    STATUS     current
    DESCRIPTION 
        "Time in seconds for the outlet to remain off when a Reboot command is issued."
    ::= { outlet17 5 }

outlet18Name  OBJECT-TYPE
    SYNTAX     OCTET STRING (SIZE(1..20))
    MAX-ACCESS read-write
    STATUS     current
    DESCRIPTION 
        "Descriptive outlet name"
    ::= { outlet18 1 }

outlet18PingIpAddress  OBJECT-TYPE
    SYNTAX     IpAddress
    MAX-ACCESS read-write
    STATUS     current
    DESCRIPTION 
        "Ping watchdog IP address"
    ::= { outlet18 2 }

outlet18Link  OBJECT-TYPE
    SYNTAX     OCTET STRING
    MAX-ACCESS read-write
    STATUS     current
    DESCRIPTION 
        "URL of web configuration interface for the device connected to this outlet."
    ::= { outlet18 3 }

outlet18SequenceTime  OBJECT-TYPE
    SYNTAX     Integer32
    MAX-ACCESS read-write
    STATUS     current
    DESCRIPTION 
        "Time in seconds for the outlet to delay turning on after a Sequence On command is issued."
    ::= { outlet18 4 }

outlet18RebootTime  OBJECT-TYPE
    SYNTAX     Integer32
    MAX-ACCESS read-write
    STATUS     current
    DESCRIPTION 
        "Time in seconds for the outlet to remain off when a Reboot command is issued."
    ::= { outlet18 5 }

outlet19Name  OBJECT-TYPE
    SYNTAX     OCTET STRING (SIZE(1..20))
    MAX-ACCESS read-write
    STATUS     current
    DESCRIPTION 
        "Descriptive outlet name"
    ::= { outlet19 1 }

outlet19PingIpAddress  OBJECT-TYPE
    SYNTAX     IpAddress
    MAX-ACCESS read-write
    STATUS     current
    DESCRIPTION 
        "Ping watchdog IP address"
    ::= { outlet19 2 }

outlet19Link  OBJECT-TYPE
    SYNTAX     OCTET STRING
    MAX-ACCESS read-write
    STATUS     current
    DESCRIPTION 
        "URL of web configuration interface for the device connected to this outlet."
    ::= { outlet19 3 }

outlet19SequenceTime  OBJECT-TYPE
    SYNTAX     Integer32
    MAX-ACCESS read-write
    STATUS     current
    DESCRIPTION 
        "Time in seconds for the outlet to delay turning on after a Sequence On command is issued."
    ::= { outlet19 4 }

outlet19RebootTime  OBJECT-TYPE
    SYNTAX     Integer32
    MAX-ACCESS read-write
    STATUS     current
    DESCRIPTION 
        "Time in seconds for the outlet to remain off when a Reboot command is issued."
    ::= { outlet19 5 }

outlet20Name  OBJECT-TYPE
    SYNTAX     OCTET STRING (SIZE(1..20))
    MAX-ACCESS read-write
    STATUS     current
    DESCRIPTION 
        "Descriptive outlet name"
    ::= { outlet20 1 }

outlet20PingIpAddress  OBJECT-TYPE
    SYNTAX     IpAddress
    MAX-ACCESS read-write
    STATUS     current
    DESCRIPTION 
        "Ping watchdog IP address"
    ::= { outlet20 2 }

outlet20Link  OBJECT-TYPE
    SYNTAX     OCTET STRING
    MAX-ACCESS read-write
    STATUS     current
    DESCRIPTION 
        "URL of web configuration interface for the device connected to this outlet."
    ::= { outlet20 3 }

outlet20SequenceTime  OBJECT-TYPE
    SYNTAX     Integer32
    MAX-ACCESS read-write
    STATUS     current
    DESCRIPTION 
        "Time in seconds for the outlet to delay turning on after a Sequence On command is issued."
    ::= { outlet20 4 }

outlet20RebootTime  OBJECT-TYPE
    SYNTAX     Integer32
    MAX-ACCESS read-write
    STATUS     current
    DESCRIPTION 
        "Time in seconds for the outlet to remain off when a Reboot command is issued."
    ::= { outlet20 5 }

outlet21Name  OBJECT-TYPE
    SYNTAX     OCTET STRING (SIZE(1..20))
    MAX-ACCESS read-write
    STATUS     current
    DESCRIPTION 
        "Descriptive outlet name"
    ::= { outlet21 1 }

outlet21PingIpAddress  OBJECT-TYPE
    SYNTAX     IpAddress
    MAX-ACCESS read-write
    STATUS     current
    DESCRIPTION 
        "Ping watchdog IP address"
    ::= { outlet21 2 }

outlet21Link  OBJECT-TYPE
    SYNTAX     OCTET STRING
    MAX-ACCESS read-write
    STATUS     current
    DESCRIPTION 
        "URL of web configuration interface for the device connected to this outlet."
    ::= { outlet21 3 }

outlet21SequenceTime  OBJECT-TYPE
    SYNTAX     Integer32
    MAX-ACCESS read-write
    STATUS     current
    DESCRIPTION 
        "Time in seconds for the outlet to delay turning on after a Sequence On command is issued."
    ::= { outlet21 4 }

outlet21RebootTime  OBJECT-TYPE
    SYNTAX     Integer32
    MAX-ACCESS read-write
    STATUS     current
    DESCRIPTION 
        "Time in seconds for the outlet to remain off when a Reboot command is issued."
    ::= { outlet21 5 }

outlet22Name  OBJECT-TYPE
    SYNTAX     OCTET STRING (SIZE(1..20))
    MAX-ACCESS read-write
    STATUS     current
    DESCRIPTION 
        "Descriptive outlet name"
    ::= { outlet22 1 }

outlet22PingIpAddress  OBJECT-TYPE
    SYNTAX     IpAddress
    MAX-ACCESS read-write
    STATUS     current
    DESCRIPTION 
        "Ping watchdog IP address"
    ::= { outlet22 2 }

outlet22Link  OBJECT-TYPE
    SYNTAX     OCTET STRING
    MAX-ACCESS read-write
    STATUS     current
    DESCRIPTION 
        "URL of web configuration interface for the device connected to this outlet."
    ::= { outlet22 3 }

outlet22SequenceTime  OBJECT-TYPE
    SYNTAX     Integer32
    MAX-ACCESS read-write
    STATUS     current
    DESCRIPTION 
        "Time in seconds for the outlet to delay turning on after a Sequence On command is issued."
    ::= { outlet22 4 }

outlet22RebootTime  OBJECT-TYPE
    SYNTAX     Integer32
    MAX-ACCESS read-write
    STATUS     current
    DESCRIPTION 
        "Time in seconds for the outlet to remain off when a Reboot command is issued."
    ::= { outlet22 5 }

outlet23Name  OBJECT-TYPE
    SYNTAX     OCTET STRING (SIZE(1..20))
    MAX-ACCESS read-write
    STATUS     current
    DESCRIPTION 
        "Descriptive outlet name"
    ::= { outlet23 1 }

outlet23PingIpAddress  OBJECT-TYPE
    SYNTAX     IpAddress
    MAX-ACCESS read-write
    STATUS     current
    DESCRIPTION 
        "Ping watchdog IP address"
    ::= { outlet23 2 }

outlet23Link  OBJECT-TYPE
    SYNTAX     OCTET STRING
    MAX-ACCESS read-write
    STATUS     current
    DESCRIPTION 
        "URL of web configuration interface for the device connected to this outlet."
    ::= { outlet23 3 }

outlet23SequenceTime  OBJECT-TYPE
    SYNTAX     Integer32
    MAX-ACCESS read-write
    STATUS     current
    DESCRIPTION 
        "Time in seconds for the outlet to delay turning on after a Sequence On command is issued."
    ::= { outlet23 4 }

outlet23RebootTime  OBJECT-TYPE
    SYNTAX     Integer32
    MAX-ACCESS read-write
    STATUS     current
    DESCRIPTION 
        "Time in seconds for the outlet to remain off when a Reboot command is issued."
    ::= { outlet23 5 }

outlet24Name  OBJECT-TYPE
    SYNTAX     OCTET STRING (SIZE(1..20))
    MAX-ACCESS read-write
    STATUS     current
    DESCRIPTION 
        "Descriptive outlet name"
    ::= { outlet24 1 }

outlet24PingIpAddress  OBJECT-TYPE
    SYNTAX     IpAddress
    MAX-ACCESS read-write
    STATUS     current
    DESCRIPTION 
        "Ping watchdog IP address"
    ::= { outlet24 2 }

outlet24Link  OBJECT-TYPE
    SYNTAX     OCTET STRING
    MAX-ACCESS read-write
    STATUS     current
    DESCRIPTION 
        "URL of web configuration interface for the device connected to this outlet."
    ::= { outlet24 3 }

outlet24SequenceTime  OBJECT-TYPE
    SYNTAX     Integer32
    MAX-ACCESS read-write
    STATUS     current
    DESCRIPTION 
        "Time in seconds for the outlet to delay turning on after a Sequence On command is issued."
    ::= { outlet24 4 }

outlet24RebootTime  OBJECT-TYPE
    SYNTAX     Integer32
    MAX-ACCESS read-write
    STATUS     current
    DESCRIPTION 
        "Time in seconds for the outlet to remain off when a Reboot command is issued."
    ::= { outlet24 5 }

outlet25Name  OBJECT-TYPE
    SYNTAX     OCTET STRING (SIZE(1..20))
    MAX-ACCESS read-write
    STATUS     current
    DESCRIPTION 
        "Descriptive outlet name"
    ::= { outlet25 1 }

outlet25PingIpAddress  OBJECT-TYPE
    SYNTAX     IpAddress
    MAX-ACCESS read-write
    STATUS     current
    DESCRIPTION 
        "Ping watchdog IP address"
    ::= { outlet25 2 }

outlet25Link  OBJECT-TYPE
    SYNTAX     OCTET STRING
    MAX-ACCESS read-write
    STATUS     current
    DESCRIPTION 
        "URL of web configuration interface for the device connected to this outlet."
    ::= { outlet25 3 }

outlet25SequenceTime  OBJECT-TYPE
    SYNTAX     Integer32
    MAX-ACCESS read-write
    STATUS     current
    DESCRIPTION 
        "Time in seconds for the outlet to delay turning on after a Sequence On command is issued."
    ::= { outlet25 4 }

outlet25RebootTime  OBJECT-TYPE
    SYNTAX     Integer32
    MAX-ACCESS read-write
    STATUS     current
    DESCRIPTION 
        "Time in seconds for the outlet to remain off when a Reboot command is issued."
    ::= { outlet25 5 }

outlet26Name  OBJECT-TYPE
    SYNTAX     OCTET STRING (SIZE(1..20))
    MAX-ACCESS read-write
    STATUS     current
    DESCRIPTION 
        "Descriptive outlet name"
    ::= { outlet26 1 }

outlet26PingIpAddress  OBJECT-TYPE
    SYNTAX     IpAddress
    MAX-ACCESS read-write
    STATUS     current
    DESCRIPTION 
        "Ping watchdog IP address"
    ::= { outlet26 2 }

outlet26Link  OBJECT-TYPE
    SYNTAX     OCTET STRING
    MAX-ACCESS read-write
    STATUS     current
    DESCRIPTION 
        "URL of web configuration interface for the device connected to this outlet."
    ::= { outlet26 3 }

outlet26SequenceTime  OBJECT-TYPE
    SYNTAX     Integer32
    MAX-ACCESS read-write
    STATUS     current
    DESCRIPTION 
        "Time in seconds for the outlet to delay turning on after a Sequence On command is issued."
    ::= { outlet26 4 }

outlet26RebootTime  OBJECT-TYPE
    SYNTAX     Integer32
    MAX-ACCESS read-write
    STATUS     current
    DESCRIPTION 
        "Time in seconds for the outlet to remain off when a Reboot command is issued."
    ::= { outlet26 5 }

outlet27Name  OBJECT-TYPE
    SYNTAX     OCTET STRING (SIZE(1..20))
    MAX-ACCESS read-write
    STATUS     current
    DESCRIPTION 
        "Descriptive outlet name"
    ::= { outlet27 1 }

outlet27PingIpAddress  OBJECT-TYPE
    SYNTAX     IpAddress
    MAX-ACCESS read-write
    STATUS     current
    DESCRIPTION 
        "Ping watchdog IP address"
    ::= { outlet27 2 }

outlet27Link  OBJECT-TYPE
    SYNTAX     OCTET STRING
    MAX-ACCESS read-write
    STATUS     current
    DESCRIPTION 
        "URL of web configuration interface for the device connected to this outlet."
    ::= { outlet27 3 }

outlet27SequenceTime  OBJECT-TYPE
    SYNTAX     Integer32
    MAX-ACCESS read-write
    STATUS     current
    DESCRIPTION 
        "Time in seconds for the outlet to delay turning on after a Sequence On command is issued."
    ::= { outlet27 4 }

outlet27RebootTime  OBJECT-TYPE
    SYNTAX     Integer32
    MAX-ACCESS read-write
    STATUS     current
    DESCRIPTION 
        "Time in seconds for the outlet to remain off when a Reboot command is issued."
    ::= { outlet27 5 }

outlet28Name  OBJECT-TYPE
    SYNTAX     OCTET STRING (SIZE(1..20))
    MAX-ACCESS read-write
    STATUS     current
    DESCRIPTION 
        "Descriptive outlet name"
    ::= { outlet28 1 }

outlet28PingIpAddress  OBJECT-TYPE
    SYNTAX     IpAddress
    MAX-ACCESS read-write
    STATUS     current
    DESCRIPTION 
        "Ping watchdog IP address"
    ::= { outlet28 2 }

outlet28Link  OBJECT-TYPE
    SYNTAX     OCTET STRING
    MAX-ACCESS read-write
    STATUS     current
    DESCRIPTION 
        "URL of web configuration interface for the device connected to this outlet."
    ::= { outlet28 3 }

outlet28SequenceTime  OBJECT-TYPE
    SYNTAX     Integer32
    MAX-ACCESS read-write
    STATUS     current
    DESCRIPTION 
        "Time in seconds for the outlet to delay turning on after a Sequence On command is issued."
    ::= { outlet28 4 }

outlet28RebootTime  OBJECT-TYPE
    SYNTAX     Integer32
    MAX-ACCESS read-write
    STATUS     current
    DESCRIPTION 
        "Time in seconds for the outlet to remain off when a Reboot command is issued."
    ::= { outlet28 5 }

outlet29Name  OBJECT-TYPE
    SYNTAX     OCTET STRING (SIZE(1..20))
    MAX-ACCESS read-write
    STATUS     current
    DESCRIPTION 
        "Descriptive outlet name"
    ::= { outlet29 1 }

outlet29PingIpAddress  OBJECT-TYPE
    SYNTAX     IpAddress
    MAX-ACCESS read-write
    STATUS     current
    DESCRIPTION 
        "Ping watchdog IP address"
    ::= { outlet29 2 }

outlet29Link  OBJECT-TYPE
    SYNTAX     OCTET STRING
    MAX-ACCESS read-write
    STATUS     current
    DESCRIPTION 
        "URL of web configuration interface for the device connected to this outlet."
    ::= { outlet29 3 }

outlet29SequenceTime  OBJECT-TYPE
    SYNTAX     Integer32
    MAX-ACCESS read-write
    STATUS     current
    DESCRIPTION 
        "Time in seconds for the outlet to delay turning on after a Sequence On command is issued."
    ::= { outlet29 4 }

outlet29RebootTime  OBJECT-TYPE
    SYNTAX     Integer32
    MAX-ACCESS read-write
    STATUS     current
    DESCRIPTION 
        "Time in seconds for the outlet to remain off when a Reboot command is issued."
    ::= { outlet29 5 }

outlet30Name  OBJECT-TYPE
    SYNTAX     OCTET STRING (SIZE(1..20))
    MAX-ACCESS read-write
    STATUS     current
    DESCRIPTION 
        "Descriptive outlet name"
    ::= { outlet30 1 }

outlet30PingIpAddress  OBJECT-TYPE
    SYNTAX     IpAddress
    MAX-ACCESS read-write
    STATUS     current
    DESCRIPTION 
        "Ping watchdog IP address"
    ::= { outlet30 2 }

outlet30Link  OBJECT-TYPE
    SYNTAX     OCTET STRING
    MAX-ACCESS read-write
    STATUS     current
    DESCRIPTION 
        "URL of web configuration interface for the device connected to this outlet."
    ::= { outlet30 3 }

outlet30SequenceTime  OBJECT-TYPE
    SYNTAX     Integer32
    MAX-ACCESS read-write
    STATUS     current
    DESCRIPTION 
        "Time in seconds for the outlet to delay turning on after a Sequence On command is issued."
    ::= { outlet30 4 }

outlet30RebootTime  OBJECT-TYPE
    SYNTAX     Integer32
    MAX-ACCESS read-write
    STATUS     current
    DESCRIPTION 
        "Time in seconds for the outlet to remain off when a Reboot command is issued."
    ::= { outlet30 5 }

outlet31Name  OBJECT-TYPE
    SYNTAX     OCTET STRING (SIZE(1..20))
    MAX-ACCESS read-write
    STATUS     current
    DESCRIPTION 
        "Descriptive outlet name"
    ::= { outlet31 1 }

outlet31PingIpAddress  OBJECT-TYPE
    SYNTAX     IpAddress
    MAX-ACCESS read-write
    STATUS     current
    DESCRIPTION 
        "Ping watchdog IP address"
    ::= { outlet31 2 }

outlet31Link  OBJECT-TYPE
    SYNTAX     OCTET STRING
    MAX-ACCESS read-write
    STATUS     current
    DESCRIPTION 
        "URL of web configuration interface for the device connected to this outlet."
    ::= { outlet31 3 }

outlet31SequenceTime  OBJECT-TYPE
    SYNTAX     Integer32
    MAX-ACCESS read-write
    STATUS     current
    DESCRIPTION 
        "Time in seconds for the outlet to delay turning on after a Sequence On command is issued."
    ::= { outlet31 4 }

outlet31RebootTime  OBJECT-TYPE
    SYNTAX     Integer32
    MAX-ACCESS read-write
    STATUS     current
    DESCRIPTION 
        "Time in seconds for the outlet to remain off when a Reboot command is issued."
    ::= { outlet31 5 }

outlet32Name  OBJECT-TYPE
    SYNTAX     OCTET STRING (SIZE(1..20))
    MAX-ACCESS read-write
    STATUS     current
    DESCRIPTION 
        "Descriptive outlet name"
    ::= { outlet32 1 }

outlet32PingIpAddress  OBJECT-TYPE
    SYNTAX     IpAddress
    MAX-ACCESS read-write
    STATUS     current
    DESCRIPTION 
        "Ping watchdog IP address"
    ::= { outlet32 2 }

outlet32Link  OBJECT-TYPE
    SYNTAX     OCTET STRING
    MAX-ACCESS read-write
    STATUS     current
    DESCRIPTION 
        "URL of web configuration interface for the device connected to this outlet."
    ::= { outlet32 3 }

outlet32SequenceTime  OBJECT-TYPE
    SYNTAX     Integer32
    MAX-ACCESS read-write
    STATUS     current
    DESCRIPTION 
        "Time in seconds for the outlet to delay turning on after a Sequence On command is issued."
    ::= { outlet32 4 }

outlet32RebootTime  OBJECT-TYPE
    SYNTAX     Integer32
    MAX-ACCESS read-write
    STATUS     current
    DESCRIPTION 
        "Time in seconds for the outlet to remain off when a Reboot command is issued."
    ::= { outlet32 5 }

outlet33Name  OBJECT-TYPE
    SYNTAX     OCTET STRING (SIZE(1..20))
    MAX-ACCESS read-write
    STATUS     current
    DESCRIPTION 
        "Descriptive outlet name"
    ::= { outlet33 1 }

outlet33PingIpAddress  OBJECT-TYPE
    SYNTAX     IpAddress
    MAX-ACCESS read-write
    STATUS     current
    DESCRIPTION 
        "Ping watchdog IP address"
    ::= { outlet33 2 }

outlet33Link  OBJECT-TYPE
    SYNTAX     OCTET STRING
    MAX-ACCESS read-write
    STATUS     current
    DESCRIPTION 
        "URL of web configuration interface for the device connected to this outlet."
    ::= { outlet33 3 }

outlet33SequenceTime  OBJECT-TYPE
    SYNTAX     Integer32
    MAX-ACCESS read-write
    STATUS     current
    DESCRIPTION 
        "Time in seconds for the outlet to delay turning on after a Sequence On command is issued."
    ::= { outlet33 4 }

outlet33RebootTime  OBJECT-TYPE
    SYNTAX     Integer32
    MAX-ACCESS read-write
    STATUS     current
    DESCRIPTION 
        "Time in seconds for the outlet to remain off when a Reboot command is issued."
    ::= { outlet33 5 }

outlet34Name  OBJECT-TYPE
    SYNTAX     OCTET STRING (SIZE(1..20))
    MAX-ACCESS read-write
    STATUS     current
    DESCRIPTION 
        "Descriptive outlet name"
    ::= { outlet34 1 }

outlet34PingIpAddress  OBJECT-TYPE
    SYNTAX     IpAddress
    MAX-ACCESS read-write
    STATUS     current
    DESCRIPTION 
        "Ping watchdog IP address"
    ::= { outlet34 2 }

outlet34Link  OBJECT-TYPE
    SYNTAX     OCTET STRING
    MAX-ACCESS read-write
    STATUS     current
    DESCRIPTION 
        "URL of web configuration interface for the device connected to this outlet."
    ::= { outlet34 3 }

outlet34SequenceTime  OBJECT-TYPE
    SYNTAX     Integer32
    MAX-ACCESS read-write
    STATUS     current
    DESCRIPTION 
        "Time in seconds for the outlet to delay turning on after a Sequence On command is issued."
    ::= { outlet34 4 }

outlet34RebootTime  OBJECT-TYPE
    SYNTAX     Integer32
    MAX-ACCESS read-write
    STATUS     current
    DESCRIPTION 
        "Time in seconds for the outlet to remain off when a Reboot command is issued."
    ::= { outlet34 5 }

outlet35Name  OBJECT-TYPE
    SYNTAX     OCTET STRING (SIZE(1..20))
    MAX-ACCESS read-write
    STATUS     current
    DESCRIPTION 
        "Descriptive outlet name"
    ::= { outlet35 1 }

outlet35PingIpAddress  OBJECT-TYPE
    SYNTAX     IpAddress
    MAX-ACCESS read-write
    STATUS     current
    DESCRIPTION 
        "Ping watchdog IP address"
    ::= { outlet35 2 }

outlet35Link  OBJECT-TYPE
    SYNTAX     OCTET STRING
    MAX-ACCESS read-write
    STATUS     current
    DESCRIPTION 
        "URL of web configuration interface for the device connected to this outlet."
    ::= { outlet35 3 }

outlet35SequenceTime  OBJECT-TYPE
    SYNTAX     Integer32
    MAX-ACCESS read-write
    STATUS     current
    DESCRIPTION 
        "Time in seconds for the outlet to delay turning on after a Sequence On command is issued."
    ::= { outlet35 4 }

outlet35RebootTime  OBJECT-TYPE
    SYNTAX     Integer32
    MAX-ACCESS read-write
    STATUS     current
    DESCRIPTION 
        "Time in seconds for the outlet to remain off when a Reboot command is issued."
    ::= { outlet35 5 }

outlet36Name  OBJECT-TYPE
    SYNTAX     OCTET STRING (SIZE(1..20))
    MAX-ACCESS read-write
    STATUS     current
    DESCRIPTION 
        "Descriptive outlet name"
    ::= { outlet36 1 }

outlet36PingIpAddress  OBJECT-TYPE
    SYNTAX     IpAddress
    MAX-ACCESS read-write
    STATUS     current
    DESCRIPTION 
        "Ping watchdog IP address"
    ::= { outlet36 2 }

outlet36Link  OBJECT-TYPE
    SYNTAX     OCTET STRING
    MAX-ACCESS read-write
    STATUS     current
    DESCRIPTION 
        "URL of web configuration interface for the device connected to this outlet."
    ::= { outlet36 3 }

outlet36SequenceTime  OBJECT-TYPE
    SYNTAX     Integer32
    MAX-ACCESS read-write
    STATUS     current
    DESCRIPTION 
        "Time in seconds for the outlet to delay turning on after a Sequence On command is issued."
    ::= { outlet36 4 }

outlet36RebootTime  OBJECT-TYPE
    SYNTAX     Integer32
    MAX-ACCESS read-write
    STATUS     current
    DESCRIPTION 
        "Time in seconds for the outlet to remain off when a Reboot command is issued."
    ::= { outlet36 5 }

globalCommand  OBJECT-TYPE
    SYNTAX     INTEGER {
        nochange (0),
        globalOn (1),
        globalOff (2),
        sequenceOn (3),
        sequenceOff (4)
    }
    MAX-ACCESS read-write
    STATUS     current
    DESCRIPTION 
        "Issue a command to all outlets on this unit."
    ::= { outletControl 1 }

outlet1Command  OBJECT-TYPE
    SYNTAX     INTEGER {
        immediateOn (1),
        immediateOff (2),
        reboot (3),
        nochange (4)
    }
    MAX-ACCESS read-write
    STATUS     current
    DESCRIPTION 
        "Issue an outlet command"
    ::= { outletControl 2 }

outlet2Command  OBJECT-TYPE
    SYNTAX     INTEGER {
        immediateOn (1),
        immediateOff (2),
        reboot (3),
        nochange (4)
    }
    MAX-ACCESS read-write
    STATUS     current
    DESCRIPTION 
        "Issue an outlet command"
    ::= { outletControl 3 }

outlet3Command  OBJECT-TYPE
    SYNTAX     INTEGER {
        immediateOn (1),
        immediateOff (2),
        reboot (3),
        nochange (4)
    }
    MAX-ACCESS read-write
    STATUS     current
    DESCRIPTION 
        "Issue an outlet command"
    ::= { outletControl 4 }

outlet4Command  OBJECT-TYPE
    SYNTAX     INTEGER {
        immediateOn (1),
        immediateOff (2),
        reboot (3),
        nochange (4)
    }
    MAX-ACCESS read-write
    STATUS     current
    DESCRIPTION 
        "Issue an outlet command"
    ::= { outletControl 5 }

outlet5Command  OBJECT-TYPE
    SYNTAX     INTEGER {
        immediateOn (1),
        immediateOff (2),
        reboot (3),
        nochange (4)
    }
    MAX-ACCESS read-write
    STATUS     current
    DESCRIPTION 
        "Issue an outlet command"
    ::= { outletControl 6 }

outlet6Command  OBJECT-TYPE
    SYNTAX     INTEGER {
        immediateOn (1),
        immediateOff (2),
        reboot (3),
        nochange (4)
    }
    MAX-ACCESS read-write
    STATUS     current
    DESCRIPTION 
        "Issue an outlet command"
    ::= { outletControl 7 }

outlet7Command  OBJECT-TYPE
    SYNTAX     INTEGER {
        immediateOn (1),
        immediateOff (2),
        reboot (3),
        nochange (4)
    }
    MAX-ACCESS read-write
    STATUS     current
    DESCRIPTION 
        "Issue an outlet command"
    ::= { outletControl 8 }

outlet8Command  OBJECT-TYPE
    SYNTAX     INTEGER {
        immediateOn (1),
        immediateOff (2),
        reboot (3),
        nochange (4)
    }
    MAX-ACCESS read-write
    STATUS     current
    DESCRIPTION 
        "Issue an outlet command"
    ::= { outletControl 9 }

outlet9Command  OBJECT-TYPE
    SYNTAX     INTEGER {
        immediateOn (1),
        immediateOff (2),
        reboot (3),
        nochange (4)
    }
    MAX-ACCESS read-write
    STATUS     current
    DESCRIPTION 
        "Issue an outlet command"
    ::= { outletControl 10 }

outlet10Command  OBJECT-TYPE
    SYNTAX     INTEGER {
        immediateOn (1),
        immediateOff (2),
        reboot (3),
        nochange (4)
    }
    MAX-ACCESS read-write
    STATUS     current
    DESCRIPTION 
        "Issue an outlet command"
    ::= { outletControl 11 }

outlet11Command  OBJECT-TYPE
    SYNTAX     INTEGER {
        immediateOn (1),
        immediateOff (2),
        reboot (3),
        nochange (4)
    }
    MAX-ACCESS read-write
    STATUS     current
    DESCRIPTION 
        "Issue an outlet command"
    ::= { outletControl 12 }

outlet12Command  OBJECT-TYPE
    SYNTAX     INTEGER {
        immediateOn (1),
        immediateOff (2),
        reboot (3),
        noChange (4)
    }
    MAX-ACCESS read-write
    STATUS     current
    DESCRIPTION 
        "Issue an outlet command"
    ::= { outletControl 13 }

outlet13Command  OBJECT-TYPE
    SYNTAX     INTEGER {
        immediateOn (1),
        immediateOff (2),
        reboot (3),
        nochange (4)
    }
    MAX-ACCESS read-write
    STATUS     current
    DESCRIPTION 
        "Issue an outlet command"
    ::= { outletControl 14 }

outlet14Command  OBJECT-TYPE
    SYNTAX     INTEGER {
        immediateOn (1),
        immediateOff (2),
        reboot (3),
        nochange (4)
    }
    MAX-ACCESS read-write
    STATUS     current
    DESCRIPTION 
        "Issue an outlet command"
    ::= { outletControl 15 }

outlet15Command  OBJECT-TYPE
    SYNTAX     INTEGER {
        immediateOn (1),
        immediateOff (2),
        reboot (3),
        nochange (4)
    }
    MAX-ACCESS read-write
    STATUS     current
    DESCRIPTION 
        "Issue an outlet command"
    ::= { outletControl 16 }

outlet16Command  OBJECT-TYPE
    SYNTAX     INTEGER {
        immediateOn (1),
        immediateOff (2),
        reboot (3),
        nochange (4)
    }
    MAX-ACCESS read-write
    STATUS     current
    DESCRIPTION 
        "Issue an outlet command"
    ::= { outletControl 17 }

outlet17Command  OBJECT-TYPE
    SYNTAX     INTEGER {
        immediateOn (1),
        immediateOff (2),
        reboot (3),
        nochange (4)
    }
    MAX-ACCESS read-write
    STATUS     current
    DESCRIPTION 
        "Issue an outlet command"
    ::= { outletControl 18 }

outlet18Command  OBJECT-TYPE
    SYNTAX     INTEGER {
        immediateOn (1),
        immediateOff (2),
        reboot (3),
        nochange (4)
    }
    MAX-ACCESS read-write
    STATUS     current
    DESCRIPTION 
        "Issue an outlet command"
    ::= { outletControl 19 }

outlet19Command  OBJECT-TYPE
    SYNTAX     INTEGER {
        immediateOn (1),
        immediateOff (2),
        reboot (3),
        nochange (4)
    }
    MAX-ACCESS read-write
    STATUS     current
    DESCRIPTION 
        "Issue an outlet command"
    ::= { outletControl 20 }

outlet20Command  OBJECT-TYPE
    SYNTAX     INTEGER {
        immediateOn (1),
        immediateOff (2),
        reboot (3),
        nochange (4)
    }
    MAX-ACCESS read-write
    STATUS     current
    DESCRIPTION 
        "Issue an outlet command"
    ::= { outletControl 21 }

outlet21Command  OBJECT-TYPE
    SYNTAX     INTEGER {
        immediateOn (1),
        immediateOff (2),
        reboot (3),
        nochange (4)
    }
    MAX-ACCESS read-write
    STATUS     current
    DESCRIPTION 
        "Issue an outlet command"
    ::= { outletControl 22 }

outlet22Command  OBJECT-TYPE
    SYNTAX     INTEGER {
        immediateOn (1),
        immediateOff (2),
        reboot (3),
        nochange (4)
    }
    MAX-ACCESS read-write
    STATUS     current
    DESCRIPTION 
        "Issue an outlet command"
    ::= { outletControl 23 }

outlet23Command  OBJECT-TYPE
    SYNTAX     INTEGER {
        immediateOn (1),
        immediateOff (2),
        reboot (3),
        nochange (4)
    }
    MAX-ACCESS read-write
    STATUS     current
    DESCRIPTION 
        "Issue an outlet command"
    ::= { outletControl 24 }

outlet24Command  OBJECT-TYPE
    SYNTAX     INTEGER {
        immediateOn (1),
        immediateOff (2),
        reboot (3),
        nochange (4)
    }
    MAX-ACCESS read-write
    STATUS     current
    DESCRIPTION 
        "Issue an outlet command"
    ::= { outletControl 25 }

outlet25Command  OBJECT-TYPE
    SYNTAX     INTEGER {
        immediateOn (1),
        immediateOff (2),
        reboot (3),
        nochange (4)
    }
    MAX-ACCESS read-write
    STATUS     current
    DESCRIPTION 
        "Issue an outlet command"
    ::= { outletControl 26 }

outlet26Command  OBJECT-TYPE
    SYNTAX     INTEGER {
        immediateOn (1),
        immediateOff (2),
        reboot (3),
        nochange (4)
    }
    MAX-ACCESS read-write
    STATUS     current
    DESCRIPTION 
        "Issue an outlet command"
    ::= { outletControl 27 }

outlet27Command  OBJECT-TYPE
    SYNTAX     INTEGER {
        immediateOn (1),
        immediateOff (2),
        reboot (3),
        nochange (4)
    }
    MAX-ACCESS read-write
    STATUS     current
    DESCRIPTION 
        "Issue an outlet command"
    ::= { outletControl 28 }

outlet28Command  OBJECT-TYPE
    SYNTAX     INTEGER {
        immediateOn (1),
        immediateOff (2),
        reboot (3),
        nochange (4)
    }
    MAX-ACCESS read-write
    STATUS     current
    DESCRIPTION 
        "Issue an outlet command"
    ::= { outletControl 29 }

outlet29Command  OBJECT-TYPE
    SYNTAX     INTEGER {
        immediateOn (1),
        immediateOff (2),
        reboot (3),
        nochange (4)
    }
    MAX-ACCESS read-write
    STATUS     current
    DESCRIPTION 
        "Issue an outlet command"
    ::= { outletControl 30 }

outlet30Command  OBJECT-TYPE
    SYNTAX     INTEGER {
        immediateOn (1),
        immediateOff (2),
        reboot (3),
        nochange (4)
    }
    MAX-ACCESS read-write
    STATUS     current
    DESCRIPTION 
        "Issue an outlet command"
    ::= { outletControl 31 }

outlet31Command  OBJECT-TYPE
    SYNTAX     INTEGER {
        immediateOn (1),
        immediateOff (2),
        reboot (3),
        nochange (4)
    }
    MAX-ACCESS read-write
    STATUS     current
    DESCRIPTION 
        "Issue an outlet command"
    ::= { outletControl 32 }

outlet32Command  OBJECT-TYPE
    SYNTAX     INTEGER {
        immediateOn (1),
        immediateOff (2),
        reboot (3),
        nochange (4)
    }
    MAX-ACCESS read-write
    STATUS     current
    DESCRIPTION 
        "Issue an outlet command"
    ::= { outletControl 33 }

outlet33Command  OBJECT-TYPE
    SYNTAX     INTEGER {
        immediateOn (1),
        immediateOff (2),
        reboot (3),
        nochange (4)
    }
    MAX-ACCESS read-write
    STATUS     current
    DESCRIPTION 
        "Issue an outlet command"
    ::= { outletControl 34 }

outlet34Command  OBJECT-TYPE
    SYNTAX     INTEGER {
        immediateOn (1),
        immediateOff (2),
        reboot (3),
        nochange (4)
    }
    MAX-ACCESS read-write
    STATUS     current
    DESCRIPTION 
        "Issue an outlet command"
    ::= { outletControl 35 }

outlet35Command  OBJECT-TYPE
    SYNTAX     INTEGER {
        immediateOn (1),
        immediateOff (2),
        reboot (3),
        nochange (4)
    }
    MAX-ACCESS read-write
    STATUS     current
    DESCRIPTION 
        "Issue an outlet command"
    ::= { outletControl 36 }

outlet36Command  OBJECT-TYPE
    SYNTAX     INTEGER {
        immediateOn (1),
        immediateOff (2),
        reboot (3),
        nochange (4)
    }
    MAX-ACCESS read-write
    STATUS     current
    DESCRIPTION 
        "Issue an outlet command"
    ::= { outletControl 37 }

outlet1Status  OBJECT-TYPE
    SYNTAX     INTEGER {
        on (1),
        off (2)
    }
    MAX-ACCESS read-only
    STATUS     current
    DESCRIPTION 
        "Get the outlet status"
    ::= { outletStatus 1 }

outlet2Status  OBJECT-TYPE
    SYNTAX     INTEGER {
        on (1),
        off (2)
    }
    MAX-ACCESS read-only
    STATUS     current
    DESCRIPTION 
        "Get the outlet status"
    ::= { outletStatus 2 }

outlet3Status  OBJECT-TYPE
    SYNTAX     INTEGER {
        on (1),
        off (2)
    }
    MAX-ACCESS read-only
    STATUS     current
    DESCRIPTION 
        "Get the outlet status"
    ::= { outletStatus 3 }

outlet4Status  OBJECT-TYPE
    SYNTAX     INTEGER {
        on (1),
        off (2)
    }
    MAX-ACCESS read-only
    STATUS     current
    DESCRIPTION 
        "Get the outlet status"
    ::= { outletStatus 4 }

outlet5Status  OBJECT-TYPE
    SYNTAX     INTEGER {
        on (1),
        off (2)
    }
    MAX-ACCESS read-only
    STATUS     current
    DESCRIPTION 
        "Get the outlet status"
    ::= { outletStatus 5 }

outlet6Status  OBJECT-TYPE
    SYNTAX     INTEGER {
        on (1),
        off (2)
    }
    MAX-ACCESS read-only
    STATUS     current
    DESCRIPTION 
        "Get the outlet status"
    ::= { outletStatus 6 }

outlet7Status  OBJECT-TYPE
    SYNTAX     INTEGER {
        on (1),
        off (2)
    }
    MAX-ACCESS read-only
    STATUS     current
    DESCRIPTION 
        "Get the outlet status"
    ::= { outletStatus 7 }

outlet8Status  OBJECT-TYPE
    SYNTAX     INTEGER {
        on (1),
        off (2)
    }
    MAX-ACCESS read-only
    STATUS     current
    DESCRIPTION 
        "Get the outlet status"
    ::= { outletStatus 8 }

outlet9Status  OBJECT-TYPE
    SYNTAX     INTEGER {
        on (1),
        off (2)
    }
    MAX-ACCESS read-only
    STATUS     current
    DESCRIPTION 
        "Get the outlet status"
    ::= { outletStatus 9 }

outlet10Status  OBJECT-TYPE
    SYNTAX     INTEGER {
        on (1),
        off (2)
    }
    MAX-ACCESS read-only
    STATUS     current
    DESCRIPTION 
        "Get the outlet status"
    ::= { outletStatus 10 }

outlet11Status  OBJECT-TYPE
    SYNTAX     INTEGER {
        on (1),
        off (2)
    }
    MAX-ACCESS read-only
    STATUS     current
    DESCRIPTION 
        "Get the outlet status"
    ::= { outletStatus 11 }

outlet12Status  OBJECT-TYPE
    SYNTAX     INTEGER {
        on (1),
        off (2)
    }
    MAX-ACCESS read-only
    STATUS     current
    DESCRIPTION 
        "Get the outlet status"
    ::= { outletStatus 12 }

outlet13Status  OBJECT-TYPE
    SYNTAX     INTEGER {
        on (1),
        off (2)
    }
    MAX-ACCESS read-only
    STATUS     current
    DESCRIPTION 
        "Get the outlet status"
    ::= { outletStatus 13 }

outlet14Status  OBJECT-TYPE
    SYNTAX     INTEGER {
        on (1),
        off (2)
    }
    MAX-ACCESS read-only
    STATUS     current
    DESCRIPTION 
        "Get the outlet status"
    ::= { outletStatus 14 }

outlet15Status  OBJECT-TYPE
    SYNTAX     INTEGER {
        on (1),
        off (2)
    }
    MAX-ACCESS read-only
    STATUS     current
    DESCRIPTION 
        "Get the outlet status"
    ::= { outletStatus 15 }

outlet16Status  OBJECT-TYPE
    SYNTAX     INTEGER {
        on (1),
        off (2)
    }
    MAX-ACCESS read-only
    STATUS     current
    DESCRIPTION 
        "Get the outlet status"
    ::= { outletStatus 16 }

outlet17Status  OBJECT-TYPE
    SYNTAX     INTEGER {
        on (1),
        off (2)
    }
    MAX-ACCESS read-only
    STATUS     current
    DESCRIPTION 
        "Get the outlet status"
    ::= { outletStatus 17 }

outlet18Status  OBJECT-TYPE
    SYNTAX     INTEGER {
        on (1),
        off (2)
    }
    MAX-ACCESS read-only
    STATUS     current
    DESCRIPTION 
        "Get the outlet status"
    ::= { outletStatus 18 }

outlet19Status  OBJECT-TYPE
    SYNTAX     INTEGER {
        on (1),
        off (2)
    }
    MAX-ACCESS read-only
    STATUS     current
    DESCRIPTION 
        "Get the outlet status"
    ::= { outletStatus 19 }

outlet20Status  OBJECT-TYPE
    SYNTAX     INTEGER {
        on (1),
        off (2)
    }
    MAX-ACCESS read-only
    STATUS     current
    DESCRIPTION 
        "Get the outlet status"
    ::= { outletStatus 20 }

outlet21Status  OBJECT-TYPE
    SYNTAX     INTEGER {
        on (1),
        off (2)
    }
    MAX-ACCESS read-only
    STATUS     current
    DESCRIPTION 
        "Get the outlet status"
    ::= { outletStatus 21 }

outlet22Status  OBJECT-TYPE
    SYNTAX     INTEGER {
        on (1),
        off (2)
    }
    MAX-ACCESS read-only
    STATUS     current
    DESCRIPTION 
        "Get the outlet status"
    ::= { outletStatus 22 }

outlet23Status  OBJECT-TYPE
    SYNTAX     INTEGER {
        on (1),
        off (2)
    }
    MAX-ACCESS read-only
    STATUS     current
    DESCRIPTION 
        "Get the outlet status"
    ::= { outletStatus 23 }

outlet24Status  OBJECT-TYPE
    SYNTAX     INTEGER {
        on (1),
        off (2)
    }
    MAX-ACCESS read-only
    STATUS     current
    DESCRIPTION 
        "Get the outlet status"
    ::= { outletStatus 24 }

outlet25Status  OBJECT-TYPE
    SYNTAX     INTEGER {
        on (1),
        off (2)
    }
    MAX-ACCESS read-only
    STATUS     current
    DESCRIPTION 
        "Get the outlet status"
    ::= { outletStatus 25 }

outlet26Status  OBJECT-TYPE
    SYNTAX     INTEGER {
        on (1),
        off (2)
    }
    MAX-ACCESS read-only
    STATUS     current
    DESCRIPTION 
        "Get the outlet status"
    ::= { outletStatus 26 }

outlet27Status  OBJECT-TYPE
    SYNTAX     INTEGER {
        on (1),
        off (2)
    }
    MAX-ACCESS read-only
    STATUS     current
    DESCRIPTION 
        "Get the outlet status"
    ::= { outletStatus 27 }

outlet28Status  OBJECT-TYPE
    SYNTAX     INTEGER {
        on (1),
        off (2)
    }
    MAX-ACCESS read-only
    STATUS     current
    DESCRIPTION 
        "Get the outlet status"
    ::= { outletStatus 28 }

outlet29Status  OBJECT-TYPE
    SYNTAX     INTEGER {
        on (1),
        off (2)
    }
    MAX-ACCESS read-only
    STATUS     current
    DESCRIPTION 
        "Get the outlet status"
    ::= { outletStatus 29 }

outlet30Status  OBJECT-TYPE
    SYNTAX     INTEGER {
        on (1),
        off (2)
    }
    MAX-ACCESS read-only
    STATUS     current
    DESCRIPTION 
        "Get the outlet status"
    ::= { outletStatus 30 }

outlet31Status  OBJECT-TYPE
    SYNTAX     INTEGER {
        on (1),
        off (2)
    }
    MAX-ACCESS read-only
    STATUS     current
    DESCRIPTION 
        "Get the outlet status"
    ::= { outletStatus 31 }

outlet32Status  OBJECT-TYPE
    SYNTAX     INTEGER {
        on (1),
        off (2)
    }
    MAX-ACCESS read-only
    STATUS     current
    DESCRIPTION 
        "Get the outlet status"
    ::= { outletStatus 32 }

outlet33Status  OBJECT-TYPE
    SYNTAX     INTEGER {
        on (1),
        off (2)
    }
    MAX-ACCESS read-only
    STATUS     current
    DESCRIPTION 
        "Get the outlet status"
    ::= { outletStatus 33 }

outlet34Status  OBJECT-TYPE
    SYNTAX     INTEGER {
        on (1),
        off (2)
    }
    MAX-ACCESS read-only
    STATUS     current
    DESCRIPTION 
        "Get the outlet status"
    ::= { outletStatus 34 }

outlet35Status  OBJECT-TYPE
    SYNTAX     INTEGER {
        on (1),
        off (2)
    }
    MAX-ACCESS read-only
    STATUS     current
    DESCRIPTION 
        "Get the outlet status"
    ::= { outletStatus 35 }

outlet36Status  OBJECT-TYPE
    SYNTAX     INTEGER {
        on (1),
        off (2)
    }
    MAX-ACCESS read-only
    STATUS     current
    DESCRIPTION 
        "Get the outlet status"
    ::= { outletStatus 36 }

publicCommunityName  OBJECT-TYPE
    SYNTAX     OCTET STRING (SIZE(1..20))
    MAX-ACCESS not-accessible
    STATUS     obsolete
    DESCRIPTION 
        "Enter the read-only community name.  Default public"
    ::= { snmpSettings 1 }

privateCommunityName  OBJECT-TYPE
    SYNTAX     OCTET STRING (SIZE(1..20))
    MAX-ACCESS not-accessible
    STATUS     obsolete
    DESCRIPTION 
        "Enter the read-write community name.  Default private"
    ::= { snmpSettings 2 }

trapCommunityName  OBJECT-TYPE
    SYNTAX     OCTET STRING (SIZE(1..20))
    MAX-ACCESS not-accessible
    STATUS     obsolete
    DESCRIPTION 
        "Enter the Trap community name.  Default public"
    ::= { snmpSettings 3 }

publicCommunityPassword  OBJECT-TYPE
    SYNTAX     OCTET STRING (SIZE(1..20))
    MAX-ACCESS not-accessible
    STATUS     obsolete
    DESCRIPTION 
        "Enter the read-only community password.  Default public"
    ::= { snmpSettings 4 }

privateCommunityPassword  OBJECT-TYPE
    SYNTAX     OCTET STRING (SIZE(1..20))
    MAX-ACCESS not-accessible
    STATUS     obsolete
    DESCRIPTION 
        "Enter the read-write community password.  Default private"
    ::= { snmpSettings 5 }

trapIpAddress  OBJECT-TYPE
    SYNTAX     IpAddress
    MAX-ACCESS read-write
    STATUS     current
    DESCRIPTION 
        "Enter the IP address to which to send SNMP traps."
    ::= { snmpSettings 6 }

snmpEnabled  OBJECT-TYPE
    SYNTAX     INTEGER {
        disabled (0),
        enabled (1)
    }
    MAX-ACCESS not-accessible
    STATUS     obsolete
    DESCRIPTION 
        "Enabled setting for SNMP interface"
    ::= { snmpSettings 7 }

trapUserLoginLogout  OBJECT-TYPE
    SYNTAX     INTEGER {
        disabled (0),
        enabled (1)
    }
    MAX-ACCESS read-write
    STATUS     current
    DESCRIPTION 
        "Enabled setting to send an SNMP trap when a user logs in/out of the serial, telnet, or web interfaces."
    ::= { snmpTraps 1 }

trapFailedLogin  OBJECT-TYPE
    SYNTAX     INTEGER {
        disabled (0),
        enabled (1)
    }
    MAX-ACCESS read-write
    STATUS     current
    DESCRIPTION 
        "Enabled setting to send an SNMP trap when a user fails to log into the serial, telnet, or web interfaces because of a username or password mismatch."
    ::= { snmpTraps 2 }

trapOutletActivity  OBJECT-TYPE
    SYNTAX     INTEGER {
        disabled (0),
        enabled (1)
    }
    MAX-ACCESS read-write
    STATUS     current
    DESCRIPTION 
        "Enabled setting to send an SNMP trap whenever an outlet changes state."
    ::= { snmpTraps 3 }

trapSystemOnOff  OBJECT-TYPE
    SYNTAX     INTEGER {
        disabled (0),
        enabled (1)
    }
    MAX-ACCESS read-write
    STATUS     current
    DESCRIPTION 
        "Enabled setting to send an SNMP trap when the PDU powers up."
    ::= { snmpTraps 4 }

trapOutletSection1Threshold  OBJECT-TYPE
    SYNTAX     INTEGER {
        disabled (0),
        enabled (1)
    }
    MAX-ACCESS read-write
    STATUS     current
    DESCRIPTION 
        "Enabled setting to send an SNMP trap when the section 1 thresholds are breached."
    ::= { snmpTraps 5 }

trapOutletSection2Threshold  OBJECT-TYPE
    SYNTAX     INTEGER {
        disabled (0),
        enabled (1)
    }
    MAX-ACCESS read-write
    STATUS     current
    DESCRIPTION 
        "Enabled setting to send an SNMP trap when the section 2 thresholds are breached."
    ::= { snmpTraps 6 }

trapOutletSection3Threshold  OBJECT-TYPE
    SYNTAX     INTEGER {
        disabled (0),
        enabled (1)
    }
    MAX-ACCESS read-write
    STATUS     current
    DESCRIPTION 
        "Enabled setting to send an SNMP trap when the section 3 thresholds are breached."
    ::= { snmpTraps 7 }

trapTemperatureSensor1Threshold  OBJECT-TYPE
    SYNTAX     INTEGER {
        disabled (0),
        enabled (1)
    }
    MAX-ACCESS read-write
    STATUS     current
    DESCRIPTION 
        "Enabled setting to send an SNMP trap when the temperature 1 sensor thresholds are breached."
    ::= { snmpTraps 8 }

trapTemperatureSensor2Threshold  OBJECT-TYPE
    SYNTAX     INTEGER {
        disabled (0),
        enabled (1)
    }
    MAX-ACCESS read-write
    STATUS     current
    DESCRIPTION 
        "Enabled setting to send an SNMP trap when the temperature 2 sensor thresholds are breached."
    ::= { snmpTraps 9 }

trapHumiditySensorThreshold  OBJECT-TYPE
    SYNTAX     INTEGER {
        disabled (0),
        enabled (1)
    }
    MAX-ACCESS read-write
    STATUS     current
    DESCRIPTION 
        "Enabled setting to send an SNMP trap when the humidity sensor thresholds are breached."
    ::= { snmpTraps 10 }

trapContactClosure1Threshold  OBJECT-TYPE
    SYNTAX     INTEGER {
        disabled (0),
        enabled (1)
    }
    MAX-ACCESS read-write
    STATUS     current
    DESCRIPTION 
        "Enabled setting to send an SNMP trap when the contact sensor 1 state changes."
    ::= { snmpTraps 11 }

trapContactClosure2Threshold  OBJECT-TYPE
    SYNTAX     INTEGER {
        disabled (0),
        enabled (1)
    }
    MAX-ACCESS read-write
    STATUS     current
    DESCRIPTION 
        "Enabled setting to send an SNMP trap when the contact sensor 2 state changes."
    ::= { snmpTraps 12 }

trapContactClosure3Threshold  OBJECT-TYPE
    SYNTAX     INTEGER {
        disabled (0),
        enabled (1)
    }
    MAX-ACCESS read-write
    STATUS     current
    DESCRIPTION 
        "Enabled setting to send an SNMP trap when the contact sensor 3 state changes."
    ::= { snmpTraps 13 }

tempSensor1Name  OBJECT-TYPE
    SYNTAX     OCTET STRING (SIZE(1..20))
    MAX-ACCESS read-write
    STATUS     current
    DESCRIPTION 
        "Descriptive sensor name"
    ::= { tempSensor1 1 }

tempSensor1Enable  OBJECT-TYPE
    SYNTAX     INTEGER {
        disabled (0),
        enabled (1)
    }
    MAX-ACCESS read-write
    STATUS     current
    DESCRIPTION 
        "When disabled, the sensor measurement is not displayed and the thresholds are ignored."
    ::= { tempSensor1 2 }

tempSensor1HighThresh  OBJECT-TYPE
    SYNTAX     Integer32 (-100..300)
    MAX-ACCESS read-write
    STATUS     current
    DESCRIPTION 
        "Sensor high threshold"
    ::= { tempSensor1 3 }

tempSensor1LowThresh  OBJECT-TYPE
    SYNTAX     Integer32 (-100..300)
    MAX-ACCESS read-write
    STATUS     current
    DESCRIPTION 
        "Sensor low threshold"
    ::= { tempSensor1 4 }

tempSensor1ControlOutlet  OBJECT-TYPE
    SYNTAX     INTEGER {
        disabled (0),
        enabled (1)
    }
    MAX-ACCESS read-write
    STATUS     current
    DESCRIPTION 
        "Enabled setting to control an outlet or group based on the sensor thresholds."
    ::= { tempSensor1 5 }

tempSensor1OutletName  OBJECT-TYPE
    SYNTAX     OCTET STRING (SIZE(1..20))
    MAX-ACCESS read-write
    STATUS     current
    DESCRIPTION 
        "Outlet or group name to control based on the sensor measurement."
    ::= { tempSensor1 6 }

tempSensor1OutletState  OBJECT-TYPE
    SYNTAX     INTEGER {
        turnOutletOn (0),
        turnOutletOff (1)
    }
    MAX-ACCESS read-write
    STATUS     current
    DESCRIPTION 
        "turnOutletOn setting will turn the outlet/group on when the thresholds are breached and off when between the thresholds.
         turnOutletOff setting will turn the outlet/group off when the thresholds are breached and on when between the thresholds."
    ::= { tempSensor1 7 }

tempSensor2Name  OBJECT-TYPE
    SYNTAX     OCTET STRING (SIZE(1..20))
    MAX-ACCESS read-write
    STATUS     current
    DESCRIPTION 
        "Descriptive sensor name"
    ::= { tempSensor2 1 }

tempSensor2Enable  OBJECT-TYPE
    SYNTAX     INTEGER {
        disabled (0),
        enabled (1)
    }
    MAX-ACCESS read-write
    STATUS     current
    DESCRIPTION 
        "When disabled, the sensor measurement is not displayed and the thresholds are ignored."
    ::= { tempSensor2 2 }

tempSensor2HighThresh  OBJECT-TYPE
    SYNTAX     Integer32 (-100..300)
    MAX-ACCESS read-write
    STATUS     current
    DESCRIPTION 
        "Sensor high threshold"
    ::= { tempSensor2 3 }

tempSensor2LowThresh  OBJECT-TYPE
    SYNTAX     Integer32 (-100..300)
    MAX-ACCESS read-write
    STATUS     current
    DESCRIPTION 
        "Sensor low threshold"
    ::= { tempSensor2 4 }

tempSensor2ControlOutlet  OBJECT-TYPE
    SYNTAX     INTEGER {
        disabled (0),
        enabled (1)
    }
    MAX-ACCESS read-write
    STATUS     current
    DESCRIPTION 
        "Enabled setting to control an outlet or group based on the sensor thresholds."
    ::= { tempSensor2 5 }

tempSensor2OutletName  OBJECT-TYPE
    SYNTAX     OCTET STRING (SIZE(1..20))
    MAX-ACCESS read-write
    STATUS     current
    DESCRIPTION 
        "Outlet or group name to control based on the sensor measurement."
    ::= { tempSensor2 6 }

tempSensor2OutletState  OBJECT-TYPE
    SYNTAX     INTEGER {
        turnOutletOn (0),
        turnOutletOff (1)
    }
    MAX-ACCESS read-write
    STATUS     current
    DESCRIPTION 
        "turnOutletOn setting will turn the outlet/group on when the thresholds are breached and off when between the thresholds.
         turnOutletOff setting will turn the outlet/group off when the thresholds are breached and on when between the thresholds."
    ::= { tempSensor2 7 }

humSensor1Name  OBJECT-TYPE
    SYNTAX     OCTET STRING (SIZE(1..20))
    MAX-ACCESS read-write
    STATUS     current
    DESCRIPTION 
        "Descriptive sensor name"
    ::= { humSensor1 1 }

humSensor1Enable  OBJECT-TYPE
    SYNTAX     INTEGER {
        disabled (0),
        enabled (1)
    }
    MAX-ACCESS read-write
    STATUS     current
    DESCRIPTION 
        "When disabled, the sensor measurement is not displayed and the thresholds are ignored."
    ::= { humSensor1 2 }

humSensor1HighThresh  OBJECT-TYPE
    SYNTAX     Integer32 (0..100)
    MAX-ACCESS read-write
    STATUS     current
    DESCRIPTION 
        "Sensor high threshold"
    ::= { humSensor1 3 }

humSensor1LowThresh  OBJECT-TYPE
    SYNTAX     Integer32 (0..100)
    MAX-ACCESS read-write
    STATUS     current
    DESCRIPTION 
        "Sensor low threshold"
    ::= { humSensor1 4 }

humSensor1ControlOutlet  OBJECT-TYPE
    SYNTAX     INTEGER {
        disabled (0),
        enabled (1)
    }
    MAX-ACCESS read-write
    STATUS     current
    DESCRIPTION 
        "Enabled setting to control an outlet or group based on the sensor thresholds."
    ::= { humSensor1 5 }

humSensor1OutletName  OBJECT-TYPE
    SYNTAX     OCTET STRING (SIZE(1..20))
    MAX-ACCESS read-write
    STATUS     current
    DESCRIPTION 
        "Outlet or group name to control based on the sensor measurement."
    ::= { humSensor1 6 }

humSensor1OutletState  OBJECT-TYPE
    SYNTAX     INTEGER {
        turnOutletOn (0),
        turnOutletOff (1)
    }
    MAX-ACCESS read-write
    STATUS     current
    DESCRIPTION 
        "turnOutletOn setting will turn the outlet/group on when the thresholds are breached and off when between the thresholds.
         turnOutletOff setting will turn the outlet/group off when the thresholds are breached and on when between the thresholds."
    ::= { humSensor1 7 }

contactClosure1Name  OBJECT-TYPE
    SYNTAX     OCTET STRING (SIZE(1..20))
    MAX-ACCESS read-write
    STATUS     current
    DESCRIPTION 
        "Descriptive sensor name"
    ::= { contactClosure1 1 }

contactClosure1Enable  OBJECT-TYPE
    SYNTAX     INTEGER {
        disabled (0),
        enabled (1)
    }
    MAX-ACCESS read-write
    STATUS     current
    DESCRIPTION 
        "When disabled, the sensor measurement is not displayed and the contact state is ignored."
    ::= { contactClosure1 2 }

contactClosure1ControlOutlet  OBJECT-TYPE
    SYNTAX     INTEGER {
        disabled (0),
        enabled (1)
    }
    MAX-ACCESS read-write
    STATUS     current
    DESCRIPTION 
        "Enabled setting to control an outlet or group based on the contact state."
    ::= { contactClosure1 3 }

contactClosure1OutletName  OBJECT-TYPE
    SYNTAX     OCTET STRING (SIZE(1..20))
    MAX-ACCESS read-write
    STATUS     current
    DESCRIPTION 
        "Outlet or group name to control based on the contact state."
    ::= { contactClosure1 4 }

contactClosure1OutletState  OBJECT-TYPE
    SYNTAX     INTEGER {
        turnOutletOn (0),
        turnOutletOff (1)
    }
    MAX-ACCESS read-write
    STATUS     current
    DESCRIPTION 
        "turnOutletOn setting will turn the outlet/group on when the contact is closed and off when the contact is open.
         turnOutletOff setting will turn the outlet/group off when the contact is open and on when the contact is closed."
    ::= { contactClosure1 5 }

contactClosure2Name  OBJECT-TYPE
    SYNTAX     OCTET STRING (SIZE(1..20))
    MAX-ACCESS read-write
    STATUS     current
    DESCRIPTION 
        "Descriptive sensor name"
    ::= { contactClosure2 1 }

contactClosure2Enable  OBJECT-TYPE
    SYNTAX     INTEGER {
        disabled (0),
        enabled (1)
    }
    MAX-ACCESS read-write
    STATUS     current
    DESCRIPTION 
        "When disabled, the sensor measurement is not displayed and the contact state is ignored."
    ::= { contactClosure2 2 }

contactClosure2ControlOutlet  OBJECT-TYPE
    SYNTAX     INTEGER {
        disabled (0),
        enabled (1)
    }
    MAX-ACCESS read-write
    STATUS     current
    DESCRIPTION 
        "Enabled setting to control an outlet or group based on the contact state."
    ::= { contactClosure2 3 }

contactClosure2OutletName  OBJECT-TYPE
    SYNTAX     OCTET STRING (SIZE(1..20))
    MAX-ACCESS read-write
    STATUS     current
    DESCRIPTION 
        "Outlet or group name to control based on the contact state."
    ::= { contactClosure2 4 }

contactClosure2OutletState  OBJECT-TYPE
    SYNTAX     INTEGER {
        turnOutletOn (0),
        turnOutletOff (1)
    }
    MAX-ACCESS read-write
    STATUS     current
    DESCRIPTION 
        "turnOutletOn setting will turn the outlet/group on when the contact is closed and off when the contact is open.
         turnOutletOff setting will turn the outlet/group off when the contact is open and on when the contact is closed."
    ::= { contactClosure2 5 }

contactClosure3Name  OBJECT-TYPE
    SYNTAX     OCTET STRING (SIZE(1..20))
    MAX-ACCESS read-write
    STATUS     current
    DESCRIPTION 
        "Descriptive sensor name"
    ::= { contactClosure3 1 }

contactClosure3Enable  OBJECT-TYPE
    SYNTAX     INTEGER {
        disabled (0),
        enabled (1)
    }
    MAX-ACCESS read-write
    STATUS     current
    DESCRIPTION 
        "When disabled, the sensor measurement is not displayed and the contact state is ignored."
    ::= { contactClosure3 2 }

contactClosure3ControlOutlet  OBJECT-TYPE
    SYNTAX     INTEGER {
        disabled (0),
        enabled (1)
    }
    MAX-ACCESS read-write
    STATUS     current
    DESCRIPTION 
        "Enabled setting to control an outlet or group based on the contact state."
    ::= { contactClosure3 3 }

contactClosure3OutletName  OBJECT-TYPE
    SYNTAX     OCTET STRING (SIZE(1..20))
    MAX-ACCESS read-write
    STATUS     current
    DESCRIPTION 
        "Outlet or group name to control based on the contact state."
    ::= { contactClosure3 4 }

contactClosure3OutletState  OBJECT-TYPE
    SYNTAX     INTEGER {
        turnOutletOn (0),
        turnOutletOff (1)
    }
    MAX-ACCESS read-write
    STATUS     current
    DESCRIPTION 
        "turnOutletOn setting will turn the outlet/group on when the contact is closed and off when the contact is open.
         turnOutletOff setting will turn the outlet/group off when the contact is open and on when the contact is closed."
    ::= { contactClosure3 5 }

outletSection1VoltageHighThreshold  OBJECT-TYPE
    SYNTAX     Integer32
    MAX-ACCESS read-write
    STATUS     current
    DESCRIPTION 
        "Upper threshold for section voltage measurement"
    ::= { outletSection1Config 1 }

outletSection1VoltageLowThreshold  OBJECT-TYPE
    SYNTAX     Integer32
    MAX-ACCESS read-write
    STATUS     current
    DESCRIPTION 
        "Lower threshold for section voltage measurement"
    ::= { outletSection1Config 2 }

outletSection1CurrentHighThreshold  OBJECT-TYPE
    SYNTAX     Integer32 (0..20)
    MAX-ACCESS read-write
    STATUS     current
    DESCRIPTION 
        "Upper threshold for section current measurement"
    ::= { outletSection1Config 3 }

outletSection1CurrentLowThreshold  OBJECT-TYPE
    SYNTAX     Integer32 (0..20)
    MAX-ACCESS read-write
    STATUS     current
    DESCRIPTION 
        "Lower threshold for section current measurement"
    ::= { outletSection1Config 4 }

outletSection1ControlOutlet  OBJECT-TYPE
    SYNTAX     INTEGER {
        disabled (0),
        enabled (1)
    }
    MAX-ACCESS read-write
    STATUS     current
    DESCRIPTION 
        "Enabled setting to control an outlet or group based on the section voltage and current thresholds."
    ::= { outletSection1Config 5 }

outletSection1OutletName  OBJECT-TYPE
    SYNTAX     OCTET STRING (SIZE(1..20))
    MAX-ACCESS read-write
    STATUS     current
    DESCRIPTION 
        "Outlet or group name to control based on the section voltage and current measurement."
    ::= { outletSection1Config 6 }

outletSection2VoltageHighThreshold  OBJECT-TYPE
    SYNTAX     Integer32
    MAX-ACCESS read-write
    STATUS     current
    DESCRIPTION 
        "Upper threshold for section voltage measurement"
    ::= { outletSection2Config 1 }

outletSection2VoltageLowThreshold  OBJECT-TYPE
    SYNTAX     Integer32
    MAX-ACCESS read-write
    STATUS     current
    DESCRIPTION 
        "Lower threshold for section voltage measurement"
    ::= { outletSection2Config 2 }

outletSection2CurrentHighThreshold  OBJECT-TYPE
    SYNTAX     Integer32 (0..20)
    MAX-ACCESS read-write
    STATUS     current
    DESCRIPTION 
        "Upper threshold for section current measurement"
    ::= { outletSection2Config 3 }

outletSection2CurrentLowThreshold  OBJECT-TYPE
    SYNTAX     Integer32 (0..20)
    MAX-ACCESS read-write
    STATUS     current
    DESCRIPTION 
        "Lower threshold for section current measurement"
    ::= { outletSection2Config 4 }

outletSection2ControlOutlet  OBJECT-TYPE
    SYNTAX     INTEGER {
        disabled (0),
        enabled (1)
    }
    MAX-ACCESS read-write
    STATUS     current
    DESCRIPTION 
        "Enabled setting to control an outlet or group based on the section voltage and current thresholds."
    ::= { outletSection2Config 5 }

outletSection2OutletName  OBJECT-TYPE
    SYNTAX     OCTET STRING (SIZE(1..20))
    MAX-ACCESS read-write
    STATUS     current
    DESCRIPTION 
        "Outlet or group name to control based on the section voltage and current measurement."
    ::= { outletSection2Config 6 }

outletSection3VoltageHighThreshold  OBJECT-TYPE
    SYNTAX     Integer32
    MAX-ACCESS read-write
    STATUS     current
    DESCRIPTION 
        "Upper threshold for section voltage measurement"
    ::= { outletSection3Config 1 }

outletSection3VoltageLowThreshold  OBJECT-TYPE
    SYNTAX     Integer32
    MAX-ACCESS read-write
    STATUS     current
    DESCRIPTION 
        "Lower threshold for section voltage measurement"
    ::= { outletSection3Config 2 }

outletSection3CurrentHighThreshold  OBJECT-TYPE
    SYNTAX     Integer32 (0..20)
    MAX-ACCESS read-write
    STATUS     current
    DESCRIPTION 
        "Upper threshold for section current measurement"
    ::= { outletSection3Config 3 }

outletSection3CurrentLowThreshold  OBJECT-TYPE
    SYNTAX     Integer32 (0..20)
    MAX-ACCESS read-write
    STATUS     current
    DESCRIPTION 
        "Lower threshold for section current measurement"
    ::= { outletSection3Config 4 }

outletSection3ControlOutlet  OBJECT-TYPE
    SYNTAX     INTEGER {
        disabled (0),
        enabled (1)
    }
    MAX-ACCESS read-write
    STATUS     current
    DESCRIPTION 
        "Enabled setting to control an outlet or group based on the section voltage and current thresholds."
    ::= { outletSection3Config 5 }

outletSection3OutletName  OBJECT-TYPE
    SYNTAX     OCTET STRING (SIZE(1..20))
    MAX-ACCESS read-write
    STATUS     current
    DESCRIPTION 
        "Outlet or group name to control based on the section voltage and current measurement."
    ::= { outletSection3Config 6 }

outletSection4VoltageHighThreshold  OBJECT-TYPE
    SYNTAX     Integer32
    MAX-ACCESS read-write
    STATUS     current
    DESCRIPTION 
        "Upper threshold for section voltage measurement"
    ::= { outletSection4Config 1 }

outletSection4VoltageLowThreshold  OBJECT-TYPE
    SYNTAX     Integer32
    MAX-ACCESS read-write
    STATUS     current
    DESCRIPTION 
        "Lower threshold for section voltage measurement"
    ::= { outletSection4Config 2 }

outletSection4CurrentHighThreshold  OBJECT-TYPE
    SYNTAX     Integer32 (0..20)
    MAX-ACCESS read-write
    STATUS     current
    DESCRIPTION 
        "Upper threshold for section current measurement"
    ::= { outletSection4Config 3 }

outletSection4CurrentLowThreshold  OBJECT-TYPE
    SYNTAX     Integer32 (0..20)
    MAX-ACCESS read-write
    STATUS     current
    DESCRIPTION 
        "Lower threshold for section current measurement"
    ::= { outletSection4Config 4 }

outletSection4ControlOutlet  OBJECT-TYPE
    SYNTAX     INTEGER {
        disabled (0),
        enabled (1)
    }
    MAX-ACCESS read-write
    STATUS     current
    DESCRIPTION 
        "Enabled setting to control an outlet or group based on the section voltage and current thresholds."
    ::= { outletSection4Config 5 }

outletSection4OutletName  OBJECT-TYPE
    SYNTAX     OCTET STRING (SIZE(1..20))
    MAX-ACCESS read-write
    STATUS     current
    DESCRIPTION 
        "Outlet or group name to control based on the section voltage and current measurement."
    ::= { outletSection4Config 6 }

outletSection5VoltageHighThreshold  OBJECT-TYPE
    SYNTAX     Integer32
    MAX-ACCESS read-write
    STATUS     current
    DESCRIPTION 
        "Upper threshold for section voltage measurement"
    ::= { outletSection5Config 1 }

outletSection5VoltageLowThreshold  OBJECT-TYPE
    SYNTAX     Integer32
    MAX-ACCESS read-write
    STATUS     current
    DESCRIPTION 
        "Lower threshold for section voltage measurement"
    ::= { outletSection5Config 2 }

outletSection5CurrentHighThreshold  OBJECT-TYPE
    SYNTAX     Integer32 (0..20)
    MAX-ACCESS read-write
    STATUS     current
    DESCRIPTION 
        "Upper threshold for section current measurement"
    ::= { outletSection5Config 3 }

outletSection5CurrentLowThreshold  OBJECT-TYPE
    SYNTAX     Integer32 (0..20)
    MAX-ACCESS read-write
    STATUS     current
    DESCRIPTION 
        "Lower threshold for section current measurement"
    ::= { outletSection5Config 4 }

outletSection5ControlOutlet  OBJECT-TYPE
    SYNTAX     INTEGER {
        disabled (0),
        enabled (1)
    }
    MAX-ACCESS read-write
    STATUS     current
    DESCRIPTION 
        "Enabled setting to control an outlet or group based on the section voltage and current thresholds."
    ::= { outletSection5Config 5 }

outletSection5OutletName  OBJECT-TYPE
    SYNTAX     OCTET STRING (SIZE(1..20))
    MAX-ACCESS read-write
    STATUS     current
    DESCRIPTION 
        "Outlet or group name to control based on the section voltage and current measurement."
    ::= { outletSection5Config 6 }

outletSection6VoltageHighThreshold  OBJECT-TYPE
    SYNTAX     Integer32
    MAX-ACCESS read-write
    STATUS     current
    DESCRIPTION 
        "Upper threshold for section voltage measurement"
    ::= { outletSection6Config 1 }

outletSection6VoltageLowThreshold  OBJECT-TYPE
    SYNTAX     Integer32
    MAX-ACCESS read-write
    STATUS     current
    DESCRIPTION 
        "Lower threshold for section voltage measurement"
    ::= { outletSection6Config 2 }

outletSection6CurrentHighThreshold  OBJECT-TYPE
    SYNTAX     Integer32 (0..20)
    MAX-ACCESS read-write
    STATUS     current
    DESCRIPTION 
        "Upper threshold for section current measurement"
    ::= { outletSection6Config 3 }

outletSection6CurrentLowThreshold  OBJECT-TYPE
    SYNTAX     Integer32 (0..20)
    MAX-ACCESS read-write
    STATUS     current
    DESCRIPTION 
        "Lower threshold for section current measurement"
    ::= { outletSection6Config 4 }

outletSection6ControlOutlet  OBJECT-TYPE
    SYNTAX     INTEGER {
        disabled (0),
        enabled (1)
    }
    MAX-ACCESS read-write
    STATUS     current
    DESCRIPTION 
        "Enabled setting to control an outlet or group based on the section voltage and current thresholds."
    ::= { outletSection6Config 5 }

outletSection6OutletName  OBJECT-TYPE
    SYNTAX     OCTET STRING (SIZE(1..20))
    MAX-ACCESS read-write
    STATUS     current
    DESCRIPTION 
        "Outlet or group name to control based on the section voltage and current measurement."
    ::= { outletSection6Config 6 }

tempSensor1Temp  OBJECT-TYPE
    SYNTAX     Integer32 (-100..300)
    MAX-ACCESS read-only
    STATUS     current
    DESCRIPTION 
        "Temperature sensor measurement (units are indicated by the fahrenheitOrCelsius leaf under the unitConfig branch)"
    ::= { currentSensorValues 1 }

tempSensor2Temp  OBJECT-TYPE
    SYNTAX     Integer32 (-100..300)
    MAX-ACCESS read-only
    STATUS     current
    DESCRIPTION 
        "Temperature sensor measurement (units are indicated by the fahrenheitOrCelsius leaf under the unitConfig branch)"
    ::= { currentSensorValues 2 }

humSensor1Humidity  OBJECT-TYPE
    SYNTAX     Integer32 (0..100)
    MAX-ACCESS read-only
    STATUS     current
    DESCRIPTION 
        "Humidity sensor measurement (percent relative humidity)"
    ::= { currentSensorValues 3 }

contactClosure1State  OBJECT-TYPE
    SYNTAX     INTEGER {
        contactOpen (0),
        contactClosed (1)
    }
    MAX-ACCESS read-only
    STATUS     current
    DESCRIPTION 
        "Contact sensor state"
    ::= { currentSensorValues 4 }

contactClosure2State  OBJECT-TYPE
    SYNTAX     INTEGER {
        contactOpen (0),
        contactClosed (1)
    }
    MAX-ACCESS read-only
    STATUS     current
    DESCRIPTION 
        "Contact sensor state"
    ::= { currentSensorValues 5 }

contactClosure3State  OBJECT-TYPE
    SYNTAX     INTEGER {
        contactOpen (0),
        contactClosed (1)
    }
    MAX-ACCESS read-only
    STATUS     current
    DESCRIPTION 
        "Contact sensor state"
    ::= { currentSensorValues 6 }

outletSection1Voltage  OBJECT-TYPE
    SYNTAX     Integer32
    MAX-ACCESS read-only
    STATUS     current
    DESCRIPTION 
        "Voltage measurement 1.  This is either the section 1 voltage, the Line X-Y voltage, or the Phase X-N voltage, depending on the PDU hardware."
    ::= { outletSection1 1 }

outletSection1Current  OBJECT-TYPE
    SYNTAX     Integer32
    MAX-ACCESS read-only
    STATUS     current
    DESCRIPTION 
        "Current measurement 1.  This is either the section 1 current or the Phase X current, depending on the PDU hardware."
    ::= { outletSection1 2 }

outletSection1Va  OBJECT-TYPE
    SYNTAX     Integer32
    MAX-ACCESS read-only
    STATUS     current
    DESCRIPTION 
        "Section 1 VA (or phase X VA, depending on the PDU hardware)."
    ::= { outletSection1 3 }

outletSection2Voltage  OBJECT-TYPE
    SYNTAX     Integer32
    MAX-ACCESS read-only
    STATUS     current
    DESCRIPTION 
        "Voltage measurement 2.  This is either the section 2 voltage, the Line Y-Z voltage, or the Phase Y-N voltage, depending on the PDU hardware."
    ::= { outletSection2 1 }

outletSection2Current  OBJECT-TYPE
    SYNTAX     Integer32
    MAX-ACCESS read-only
    STATUS     current
    DESCRIPTION 
        "Current measurement 2.  This is either the section 2 current or the Phase Y current, depending on the PDU hardware."
    ::= { outletSection2 2 }

outletSection2Va  OBJECT-TYPE
    SYNTAX     Integer32
    MAX-ACCESS read-only
    STATUS     current
    DESCRIPTION 
        "Section 2 VA (or phase Y VA, depending on the PDU hardware)."
    ::= { outletSection2 3 }

outletSection3Voltage  OBJECT-TYPE
    SYNTAX     Integer32
    MAX-ACCESS read-only
    STATUS     current
    DESCRIPTION 
        "Voltage measurement 3.  This is either the section 3 voltage, the Line Z-X voltage, or the Phase Z-N voltage, depending on the PDU hardware."
    ::= { outletSection3 1 }

outletSection3Current  OBJECT-TYPE
    SYNTAX     Integer32
    MAX-ACCESS read-only
    STATUS     current
    DESCRIPTION 
        "Current measurement 3.  This is either the section 3 current or the Phase Z current, depending on the PDU hardware."
    ::= { outletSection3 2 }

outletSection3Va  OBJECT-TYPE
    SYNTAX     Integer32
    MAX-ACCESS read-only
    STATUS     current
    DESCRIPTION 
        "Section 3 VA (or phase Z VA, depending on the PDU hardware)."
    ::= { outletSection3 3 }

totalVoltage  OBJECT-TYPE
    SYNTAX     Integer32
    MAX-ACCESS read-only
    STATUS     obsolete
    DESCRIPTION 
        "None"
    ::= { total 1 }

totalCurrent  OBJECT-TYPE
    SYNTAX     Integer32
    MAX-ACCESS read-only
    STATUS     current
    DESCRIPTION 
        "Sum of current for all outlet sections (or phases)"
    ::= { total 2 }

totalVa  OBJECT-TYPE
    SYNTAX     Integer32
    MAX-ACCESS read-only
    STATUS     current
    DESCRIPTION 
        "Total PDU VA"
    ::= { total 3 }

outletSection4Voltage  OBJECT-TYPE
    SYNTAX     Integer32
    MAX-ACCESS read-only
    STATUS     current
    DESCRIPTION 
        "Voltage measurement 4 (section 4 voltage).  This object will not be present if the PDU hardware measures Line-to-Line voltage or Phase voltage."
    ::= { outletSection4 1 }

outletSection4Current  OBJECT-TYPE
    SYNTAX     Integer32
    MAX-ACCESS read-only
    STATUS     current
    DESCRIPTION 
        "Current measurement 4.  This is the section 4 current."
    ::= { outletSection4 2 }

outletSection4Va  OBJECT-TYPE
    SYNTAX     Integer32
    MAX-ACCESS read-only
    STATUS     current
    DESCRIPTION 
        "Section 4 VA"
    ::= { outletSection4 3 }

outletSection5Voltage  OBJECT-TYPE
    SYNTAX     Integer32
    MAX-ACCESS read-only
    STATUS     current
    DESCRIPTION 
        "Voltage measurement 5 (section 5 voltage).  This object will not be present if the PDU hardware measures Line-to-Line voltage or Phase voltage."
    ::= { outletSection5 1 }

outletSection5Current  OBJECT-TYPE
    SYNTAX     Integer32
    MAX-ACCESS read-only
    STATUS     current
    DESCRIPTION 
        "Current measurement 5.  This is the section 5 current."
    ::= { outletSection5 2 }

outletSection5Va  OBJECT-TYPE
    SYNTAX     Integer32
    MAX-ACCESS read-only
    STATUS     current
    DESCRIPTION 
        "Section 5 VA"
    ::= { outletSection5 3 }

outletSection6Voltage  OBJECT-TYPE
    SYNTAX     Integer32
    MAX-ACCESS read-only
    STATUS     current
    DESCRIPTION 
        "Voltage measurement 6 (section 6 voltage).  This object will not be present if the PDU hardware measures Line-to-Line voltage or Phase voltage."
    ::= { outletSection6 1 }

outletSection6Current  OBJECT-TYPE
    SYNTAX     Integer32
    MAX-ACCESS read-only
    STATUS     current
    DESCRIPTION 
        "Current measurement 6.  This is the section 6 current."
    ::= { outletSection6 2 }

outletSection6Va  OBJECT-TYPE
    SYNTAX     Integer32
    MAX-ACCESS read-only
    STATUS     current
    DESCRIPTION 
        "Section 6 VA"
    ::= { outletSection6 3 }

notifyOutletState  NOTIFICATION-TYPE
    OBJECTS { infoItemIdx, 
        infoItemName, 
        infoOutletState }
    STATUS     current
    DESCRIPTION 
        "Outlet state has changed."
    ::= { events 1 }

notifyCurrentThreshold  NOTIFICATION-TYPE
    OBJECTS { infoItemIdx, 
        infoItemName, 
        infoThresholdState, 
        infoThresholdValue, 
        infoMeasuredValue }
    STATUS     current
    DESCRIPTION 
        "Current measurement has exceeded a threshold or returned from crossing a threshold."
    ::= { events 2 }

notifyVoltageThreshold  NOTIFICATION-TYPE
    OBJECTS { infoItemIdx, 
        infoItemName, 
        infoThresholdState, 
        infoThresholdValue, 
        infoMeasuredValue }
    STATUS     current
    DESCRIPTION 
        "Voltage measurement has exceeded a threshold or returned from crossing a threshold."
    ::= { events 3 }

notifyTempSensorThreshold  NOTIFICATION-TYPE
    OBJECTS { infoItemIdx, 
        infoItemName, 
        infoThresholdState, 
        infoThresholdValue, 
        infoMeasuredValue, 
        fahrenheitOrCelsius }
    STATUS     current
    DESCRIPTION 
        "Temperature measurement has exceeded a threshold or returned from crossing a threshold."
    ::= { events 4 }

notifyHumidSensorThreshold  NOTIFICATION-TYPE
    OBJECTS { infoItemIdx, 
        infoItemName, 
        infoThresholdState, 
        infoThresholdValue, 
        infoMeasuredValue }
    STATUS     current
    DESCRIPTION 
        "Humidity measurement has exceeded a threshold or returned from crossing a threshold."
    ::= { events 5 }

notifyContactSensorThreshold  NOTIFICATION-TYPE
    OBJECTS { infoItemIdx, 
        infoItemName, 
        infoContactState }
    STATUS     current
    DESCRIPTION 
        "Contact sensor has changed state."
    ::= { events 6 }

notifyUserLogin  NOTIFICATION-TYPE
    OBJECTS { infoUserName }
    STATUS     current
    DESCRIPTION 
        "A user has logged in."
    ::= { events 7 }

notifyUserLogout  NOTIFICATION-TYPE
    OBJECTS { infoUserName }
    STATUS     current
    DESCRIPTION 
        "A user has logged out."
    ::= { events 8 }

notifyFailedLogin  NOTIFICATION-TYPE
    OBJECTS { infoUserName }
    STATUS     current
    DESCRIPTION 
        "A login failure occurred."
    ::= { events 9 }

notifyOutletWatchdogFailed  NOTIFICATION-TYPE
    OBJECTS { infoItemIdx, 
        infoItemName }
    STATUS     current
    DESCRIPTION 
        "An outlet watchdog has failed and the corresponding outlet is being rebooted."
    ::= { events 10 }

infoItemIdx  OBJECT-TYPE
    SYNTAX     Integer32
    MAX-ACCESS accessible-for-notify
    STATUS     current
    DESCRIPTION 
        "Numerical index of the item that caused the notification.  For example, if the notification
        was related to the state of outlet 5, this value will be 5 no matter what the customized
        outlet name is.  Similarly, if the notification was related to a voltage threshold being
        exceeded for voltage measurement 2, this value will be 2."
    ::= { eventInfo 1 }

infoItemName  OBJECT-TYPE
    SYNTAX     OCTET STRING
    MAX-ACCESS accessible-for-notify
    STATUS     current
    DESCRIPTION 
        "Textual name of the item that caused the notification.  For example, if an outlet
        state change caused the notification, this will be the customized name of the outlet.
        If a voltage threshold caused the notification, this will be the fixed name of the voltage
        measurement (e.g., Line X-Y)."
    ::= { eventInfo 2 }

infoOutletState  OBJECT-TYPE
    SYNTAX     INTEGER {
        on (1),
        off (2)
    }
    MAX-ACCESS accessible-for-notify
    STATUS     current
    DESCRIPTION 
        "The new state of an outlet."
    ::= { eventInfo 3 }

infoThresholdState  OBJECT-TYPE
    SYNTAX     INTEGER {
        good (0),
        lowWarning (1),
        highWarning (3)
    }
    MAX-ACCESS accessible-for-notify
    STATUS     current
    DESCRIPTION 
        "The new state of a measurement that has upper and lower thresholds."
    ::= { eventInfo 4 }

infoThresholdValue  OBJECT-TYPE
    SYNTAX     Integer32 (-100..300)
    MAX-ACCESS accessible-for-notify
    STATUS     current
    DESCRIPTION 
        "The threshold which has been crossed."
    ::= { eventInfo 5 }

infoMeasuredValue  OBJECT-TYPE
    SYNTAX     Integer32 (-100..300)
    MAX-ACCESS accessible-for-notify
    STATUS     current
    DESCRIPTION 
        "The actual measured value."
    ::= { eventInfo 6 }

infoContactState  OBJECT-TYPE
    SYNTAX     INTEGER {
        contactOpen (0),
        contactClosed (1)
    }
    MAX-ACCESS accessible-for-notify
    STATUS     current
    DESCRIPTION 
        "The new state of a contact switch sensor."
    ::= { eventInfo 7 }

infoUserName  OBJECT-TYPE
    SYNTAX     OCTET STRING
    MAX-ACCESS accessible-for-notify
    STATUS     current
    DESCRIPTION 
        "Login name of a user."
    ::= { eventInfo 8 }

compliances  MODULE-COMPLIANCE
    STATUS     current
    DESCRIPTION 
        "The requirements for conforming to the Switched ePDU MIB."
    MODULE
        GROUP allObjects
        DESCRIPTION 
        "All objects group."
        GROUP allNotifications
        DESCRIPTION 
        "All notifications group."
    ::= { conformance 1 }

oldCompliances  MODULE-COMPLIANCE
    STATUS     deprecated
    DESCRIPTION 
        "Deprecated requirements for conforming to the Switched ePDU MIB."
    MODULE
        GROUP oldObjects
        DESCRIPTION 
        "Deprecated objects"
    ::= { conformance 2 }

obsoleteCompliances  MODULE-COMPLIANCE
    STATUS     obsolete
    DESCRIPTION 
        "Obsoleted requirements for conforming to the Switched ePDU MIB."
    MODULE
        GROUP obsoleteObjects
        DESCRIPTION 
        "Obsolete objects"
    ::= { conformance 3 }

allObjects  OBJECT-GROUP
    OBJECTS { baudRate, 
        contactClosure1Alert, 
        contactClosure1ControlOutlet, 
        contactClosure1Enable, 
        contactClosure1Name, 
        contactClosure1OutletName, 
        contactClosure1OutletState, 
        contactClosure1State, 
        contactClosure2Alert, 
        contactClosure2ControlOutlet, 
        contactClosure2Enable, 
        contactClosure2Name, 
        contactClosure2OutletName, 
        contactClosure2OutletState, 
        contactClosure2State, 
        contactClosure3Alert, 
        contactClosure3ControlOutlet, 
        contactClosure3Enable, 
        contactClosure3Name, 
        contactClosure3OutletName, 
        contactClosure3OutletState, 
        contactClosure3State, 
        defaultGateway, 
        enablePing, 
        fahrenheitOrCelsius, 
        globalCommand, 
        humSensor1Alert, 
        humSensor1ControlOutlet, 
        humSensor1Enable, 
        humSensor1HighThresh, 
        humSensor1Humidity, 
        humSensor1LowThresh, 
        humSensor1Name, 
        humSensor1OutletName, 
        humSensor1OutletState, 
        infoContactState, 
        infoItemIdx, 
        infoItemName, 
        infoMeasuredValue, 
        infoOutletState, 
        infoThresholdState, 
        infoThresholdValue, 
        infoUserName, 
        invertDisplay, 
        loginTimeout, 
        macAddress, 
        mailServerIPAddress, 
        outlet10Command, 
        outlet10Link, 
        outlet10Name, 
        outlet10PingIpAddress, 
        outlet10RebootTime, 
        outlet10SequenceTime, 
        outlet10Status, 
        outlet11Command, 
        outlet11Link, 
        outlet11Name, 
        outlet11PingIpAddress, 
        outlet11RebootTime, 
        outlet11SequenceTime, 
        outlet11Status, 
        outlet12Command, 
        outlet12Link, 
        outlet12Name, 
        outlet12PingIpAddress, 
        outlet12RebootTime, 
        outlet12SequenceTime, 
        outlet12Status, 
        outlet13Command, 
        outlet13Link, 
        outlet13Name, 
        outlet13PingIpAddress, 
        outlet13RebootTime, 
        outlet13SequenceTime, 
        outlet13Status, 
        outlet14Command, 
        outlet14Link, 
        outlet14Name, 
        outlet14PingIpAddress, 
        outlet14RebootTime, 
        outlet14SequenceTime, 
        outlet14Status, 
        outlet15Command, 
        outlet15Link, 
        outlet15Name, 
        outlet15PingIpAddress, 
        outlet15RebootTime, 
        outlet15SequenceTime, 
        outlet15Status, 
        outlet16Command, 
        outlet16Link, 
        outlet16Name, 
        outlet16PingIpAddress, 
        outlet16RebootTime, 
        outlet16SequenceTime, 
        outlet16Status, 
        outlet17Command, 
        outlet17Link, 
        outlet17Name, 
        outlet17PingIpAddress, 
        outlet17RebootTime, 
        outlet17SequenceTime, 
        outlet17Status, 
        outlet18Command, 
        outlet18Link, 
        outlet18Name, 
        outlet18PingIpAddress, 
        outlet18RebootTime, 
        outlet18SequenceTime, 
        outlet18Status, 
        outlet19Command, 
        outlet19Link, 
        outlet19Name, 
        outlet19PingIpAddress, 
        outlet19RebootTime, 
        outlet19SequenceTime, 
        outlet19Status, 
        outlet1Command, 
        outlet1Link, 
        outlet1Name, 
        outlet1PingIpAddress, 
        outlet1RebootTime, 
        outlet1SequenceTime, 
        outlet1Status, 
        outlet20Command, 
        outlet20Link, 
        outlet20Name, 
        outlet20PingIpAddress, 
        outlet20RebootTime, 
        outlet20SequenceTime, 
        outlet20Status, 
        outlet21Command, 
        outlet21Link, 
        outlet21Name, 
        outlet21PingIpAddress, 
        outlet21RebootTime, 
        outlet21SequenceTime, 
        outlet21Status, 
        outlet22Command, 
        outlet22Link, 
        outlet22Name, 
        outlet22PingIpAddress, 
        outlet22RebootTime, 
        outlet22SequenceTime, 
        outlet22Status, 
        outlet23Command, 
        outlet23Link, 
        outlet23Name, 
        outlet23PingIpAddress, 
        outlet23RebootTime, 
        outlet23SequenceTime, 
        outlet23Status, 
        outlet24Command, 
        outlet24Link, 
        outlet24Name, 
        outlet24PingIpAddress, 
        outlet24RebootTime, 
        outlet24SequenceTime, 
        outlet24Status, 
        outlet25Command, 
        outlet25Link, 
        outlet25Name, 
        outlet25PingIpAddress, 
        outlet25RebootTime, 
        outlet25SequenceTime, 
        outlet25Status, 
        outlet26Command, 
        outlet26Link, 
        outlet26Name, 
        outlet26PingIpAddress, 
        outlet26RebootTime, 
        outlet26SequenceTime, 
        outlet26Status, 
        outlet27Command, 
        outlet27Link, 
        outlet27Name, 
        outlet27PingIpAddress, 
        outlet27RebootTime, 
        outlet27SequenceTime, 
        outlet27Status, 
        outlet28Command, 
        outlet28Link, 
        outlet28Name, 
        outlet28PingIpAddress, 
        outlet28RebootTime, 
        outlet28SequenceTime, 
        outlet28Status, 
        outlet29Command, 
        outlet29Link, 
        outlet29Name, 
        outlet29PingIpAddress, 
        outlet29RebootTime, 
        outlet29SequenceTime, 
        outlet29Status, 
        outlet2Command, 
        outlet2Link, 
        outlet2Name, 
        outlet2PingIpAddress, 
        outlet2RebootTime, 
        outlet2SequenceTime, 
        outlet2Status, 
        outlet30Command, 
        outlet30Link, 
        outlet30Name, 
        outlet30PingIpAddress, 
        outlet30RebootTime, 
        outlet30SequenceTime, 
        outlet30Status, 
        outlet31Command, 
        outlet31Link, 
        outlet31Name, 
        outlet31PingIpAddress, 
        outlet31RebootTime, 
        outlet31SequenceTime, 
        outlet31Status, 
        outlet32Command, 
        outlet32Link, 
        outlet32Name, 
        outlet32PingIpAddress, 
        outlet32RebootTime, 
        outlet32SequenceTime, 
        outlet32Status, 
        outlet33Command, 
        outlet33Link, 
        outlet33Name, 
        outlet33PingIpAddress, 
        outlet33RebootTime, 
        outlet33SequenceTime, 
        outlet33Status, 
        outlet34Command, 
        outlet34Link, 
        outlet34Name, 
        outlet34PingIpAddress, 
        outlet34RebootTime, 
        outlet34SequenceTime, 
        outlet34Status, 
        outlet35Command, 
        outlet35Link, 
        outlet35Name, 
        outlet35PingIpAddress, 
        outlet35RebootTime, 
        outlet35SequenceTime, 
        outlet35Status, 
        outlet36Command, 
        outlet36Link, 
        outlet36Name, 
        outlet36PingIpAddress, 
        outlet36RebootTime, 
        outlet36SequenceTime, 
        outlet36Status, 
        outlet3Command, 
        outlet3Link, 
        outlet3Name, 
        outlet3PingIpAddress, 
        outlet3RebootTime, 
        outlet3SequenceTime, 
        outlet3Status, 
        outlet4Command, 
        outlet4Link, 
        outlet4Name, 
        outlet4PingIpAddress, 
        outlet4RebootTime, 
        outlet4SequenceTime, 
        outlet4Status, 
        outlet5Command, 
        outlet5Link, 
        outlet5Name, 
        outlet5PingIpAddress, 
        outlet5RebootTime, 
        outlet5SequenceTime, 
        outlet5Status, 
        outlet6Command, 
        outlet6Link, 
        outlet6Name, 
        outlet6PingIpAddress, 
        outlet6RebootTime, 
        outlet6SequenceTime, 
        outlet6Status, 
        outlet7Command, 
        outlet7Link, 
        outlet7Name, 
        outlet7PingIpAddress, 
        outlet7RebootTime, 
        outlet7SequenceTime, 
        outlet7Status, 
        outlet8Command, 
        outlet8Link, 
        outlet8Name, 
        outlet8PingIpAddress, 
        outlet8RebootTime, 
        outlet8SequenceTime, 
        outlet8Status, 
        outlet9Command, 
        outlet9Link, 
        outlet9Name, 
        outlet9PingIpAddress, 
        outlet9RebootTime, 
        outlet9SequenceTime, 
        outlet9Status, 
        outletActivity, 
        outletSection1Alert, 
        outletSection1Current, 
        outletSection1CurrentHighThreshold, 
        outletSection1CurrentLowThreshold, 
        outletSection1Va, 
        outletSection1Voltage, 
        outletSection1VoltageHighThreshold, 
        outletSection1VoltageLowThreshold, 
        outletSection2Alert, 
        outletSection2Current, 
        outletSection2CurrentHighThreshold, 
        outletSection2CurrentLowThreshold, 
        outletSection2Va, 
        outletSection2Voltage, 
        outletSection2VoltageHighThreshold, 
        outletSection2VoltageLowThreshold, 
        outletSection3Alert, 
        outletSection3Current, 
        outletSection3CurrentHighThreshold, 
        outletSection3CurrentLowThreshold, 
        outletSection3Va, 
        outletSection3Voltage, 
        outletSection3VoltageHighThreshold, 
        outletSection3VoltageLowThreshold, 
        outletSection4Current, 
        outletSection4CurrentHighThreshold, 
        outletSection4CurrentLowThreshold, 
        outletSection4Va, 
        outletSection4Voltage, 
        outletSection4VoltageHighThreshold, 
        outletSection4VoltageLowThreshold, 
        outletSection5Current, 
        outletSection5CurrentHighThreshold, 
        outletSection5CurrentLowThreshold, 
        outletSection5Va, 
        outletSection5Voltage, 
        outletSection5VoltageHighThreshold, 
        outletSection5VoltageLowThreshold, 
        outletSection6Current, 
        outletSection6CurrentHighThreshold, 
        outletSection6CurrentLowThreshold, 
        outletSection6Va, 
        outletSection6Voltage, 
        outletSection6VoltageHighThreshold, 
        outletSection6VoltageLowThreshold, 
        pingInterval, 
        sendAlertsToUser1Address, 
        sendAlertsToUser2Address, 
        sendLogFrequency, 
        sendLogFrom, 
        sendLogTime, 
        sendLogToUser1Address, 
        sendLogToUser2Address, 
        strappingId, 
        subnetMask, 
        systemOnOff, 
        telnetEnabled, 
        telnetPort, 
        tempSensor1Alert, 
        tempSensor1ControlOutlet, 
        tempSensor1Enable, 
        tempSensor1HighThresh, 
        tempSensor1LowThresh, 
        tempSensor1Name, 
        tempSensor1OutletName, 
        tempSensor1OutletState, 
        tempSensor1Temp, 
        tempSensor2Alert, 
        tempSensor2ControlOutlet, 
        tempSensor2Enable, 
        tempSensor2HighThresh, 
        tempSensor2LowThresh, 
        tempSensor2Name, 
        tempSensor2OutletName, 
        tempSensor2OutletState, 
        tempSensor2Temp, 
        totalCurrent, 
        totalVa, 
        trapContactClosure1Threshold, 
        trapContactClosure2Threshold, 
        trapContactClosure3Threshold, 
        trapFailedLogin, 
        trapHumiditySensorThreshold, 
        trapIpAddress, 
        trapOutletActivity, 
        trapOutletSection1Threshold, 
        trapOutletSection2Threshold, 
        trapOutletSection3Threshold, 
        trapSystemOnOff, 
        trapTemperatureSensor1Threshold, 
        trapTemperatureSensor2Threshold, 
        trapUserLoginLogout, 
        unitDate, 
        unitDayOfWeek, 
        unitIPAddress, 
        unitName, 
        unitTime, 
        userLogInLogOut, 
        userLogInLogOutFailed, 
        vaLoggingInterval, 
        webEnabled, 
        webPort }
    STATUS     current
    DESCRIPTION 
        "The object group."
    ::= { groups 1 }

oldObjects  OBJECT-GROUP
    OBJECTS { outletSection1ControlOutlet, 
        outletSection1OutletName, 
        outletSection2ControlOutlet, 
        outletSection2OutletName, 
        outletSection3ControlOutlet, 
        outletSection3OutletName, 
        outletSection4ControlOutlet, 
        outletSection4OutletName, 
        outletSection5ControlOutlet, 
        outletSection5OutletName, 
        outletSection6ControlOutlet, 
        outletSection6OutletName }
    STATUS     deprecated
    DESCRIPTION 
        "The deprecated objects group."
    ::= { groups 2 }

obsoleteObjects  OBJECT-GROUP
    OBJECTS { totalVoltage }
    STATUS     obsolete
    DESCRIPTION 
        "The obsoleted objects group."
    ::= { groups 3 }

allNotifications  NOTIFICATION-GROUP
    NOTIFICATIONS { notifyContactSensorThreshold, 
        notifyCurrentThreshold, 
        notifyFailedLogin, 
        notifyHumidSensorThreshold, 
        notifyOutletState, 
        notifyOutletWatchdogFailed, 
        notifyTempSensorThreshold, 
        notifyUserLogin, 
        notifyUserLogout, 
        notifyVoltageThreshold }
    STATUS     current
    DESCRIPTION 
        "The notifications group."
    ::= { groups 4 }
END
